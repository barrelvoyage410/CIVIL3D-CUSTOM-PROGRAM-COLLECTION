;  $Id: laytools.lsp,v 1.1.1.1 1993/10/18 17:55:29 rlm Exp $


;*LAYTOOLS.LSP               4/11/1990  PMH  
;*Version 11.00 Steel Detailer
;*Version 10.10 Structural Designer

;; decompiled for R14 on 7-14-1998 for CGL by ME

(defun laytools (opt / en1 s1 s2 v1)
  (cond
    ((= opt "SET")
      (if (setq en1 (entsel "\nSelect object for current layer: "))
        (command "_.LAYER" "_S" (cdr (assoc 8 (entget (car en1)))) "")
        (prompt "\nNo object selected.")
      )
    )
    ((= opt "OFF")
      (while (setq en1 (entsel "\nSelect object on layer to turn off: "))
        (setq s1 (cdr (assoc 8 (entget (car en1)))))
        (prompt (strcat "\nTurning off layer " s1))
        (if (and (= s1 (getvar "CLAYER")) (zerop (getvar "EXPERT")))
          (command "_.LAYER" "_OFF" s1 "_Y" "")
          (command "_.LAYER" "_OFF" s1 "")
        )
      )
      (prompt "\nNo object selected.")
    )
    ((= opt "FRZ")
      (while (setq en1 (entsel "\nSelect object on layer to freeze: "))
        (setq s1 (cdr (assoc 8 (entget (car en1)))))
        (if (= s1 (getvar "CLAYER"))
          (prompt (strcat "\nCannot freeze layer " s1 ". It is the CURRENT layer."))
          (progn
             (prompt (strcat "\nFreezing layer " s1))
             (command "_.LAYER" "_FREEZE" s1 "")
          )
        )
      )
      (prompt "\nNo object selected.")
    )
    ((= opt "ISO")
      (if (setq en1 (entsel "\nSelect object on layer to isolate: "))
        (progn
          (setq s1 (cdr (assoc 8 (entget (car en1)))))
          (prompt (strcat "\nIsolating layer " s1))
          (if (zerop (getvar "EXPERT"))
            (command "_.LAYER" "_OFF" "*" "_Y" "_ON" s1 "")
            (command "_.LAYER" "_OFF" "*" "_ON" s1 "")
          )
        )
        (prompt "\nNo object selected.")
      )
    )
    ((= opt "PRO")
      (while (setq en1 (entsel "\nSelect object to change layer properties: "))
        (setq
          s1 (cdr (assoc 8 (entget (car en1))))
          en1 (tblsearch "LAYER" s1)
          v1 (cdr (assoc 62 en1))
          s2 (cdr (assoc 6 en1))
        )
        (setq ans(getint (strcat "\nNew color number <" (itoa v1) ">: ")))
        (if (not (null ans))
           (setq v1 ans)
        )
        (setq ans(getstring (strcat "\nNew linetype <" s2 ">: ")))
        (if (> (strlen ans) 0)
           (setq s2 ans)
        )
        (command "_.LAYER" "_C" v1 s1 "_L" s2 s1 "")
      )
      (prompt "\nNo object selected.")
    )
    ((= opt "ID")
      (while (setq en1 (entsel "\nSelect object: "))
        (prompt (strcat "\nObject is on layer "
                         (cdr (assoc 8 (entget (car en1))))
                ))
      )
      (prompt "\nNo object selected.")
    )
  )
  (princ)
)
(princ)
