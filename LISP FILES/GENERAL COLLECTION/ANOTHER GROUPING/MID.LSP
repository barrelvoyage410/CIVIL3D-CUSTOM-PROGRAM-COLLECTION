(DEFUN C:MID (/ P01 P02)
        (INITGET 1)
        (SETQ P01 (GETPOINT (GETVAR "LASTPOINT") "\nFIRST POINT: ")
              P02 (GETPOINT P01 "\nSECOND POINT: "))
        (POLAR P01 (ANGLE P01 P02) (/ (DISTANCE P01 P02) 2.0))
);END MID.LSP
