;;; Calculate difference in elevation
(defun c:zdif (/ pt1 pt2 x1 y1 z1 x2 y2 z2)
  (setq os (getvar 'osmode))
  (setvar 'osmode 135)
  (command "_UCS" "")
  (princ "Calculate Difference in Elevation")
  (setq pt1 (getpoint "\nSelect First Point"))
  (setq pt2 (getpoint "\nSelect Second Point"))
  (setq x1 (nth 0 Pt1))
  (setq y1 (nth 1 Pt1))
  (setq z1 (nth 2 Pt1))
  (setq x2 (nth 0 pt2))
  (setq y2 (nth 1 pt2))
  (setq z2 (nth 2 pt2))
  (alert (strcat "Difference in Elevation = " (rtos(- z1 z2)))
	 )
  (setvar 'osmode os)
  (princ)
  )
