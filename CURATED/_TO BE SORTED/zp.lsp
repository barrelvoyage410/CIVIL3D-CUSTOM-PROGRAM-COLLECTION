:sets all lines to zero elevation

(DEFUN C:ZP2 ()
(graphscr)
(setq FNM (getstring "Enter name of TEXT file to create: "))
(setq FNM (strcat FNM ".txt"))
(setq FD (open FNM "w"))
(setq HEAD "POINT \t\tX \t\tY \t\tELEV")
(write-line "Exported coordinates:-" FD)
(princ "\n" FD)
(write-line HEAD FD)
(princ "\n" FD)
(if (Null PN)(setq PN 1))
(prompt "\nEnter first point reference number <")
(princ PN)
(setq PNN (getint ">: "))
(if (Null PNN)(setq PN PN)(setq PN PNN))
(setq A1 (getpoint "\nSelect bottom left corner of area to be selected: "))
(initget 32)
(setq A2 (getcorner A1 "\nSelect top right corner of area to be selected: "))
(setq S1 (ssget "c" A1 A2 (LIST (CONS 0 "insert"))))
(setq SSL (sslength S1))
(setq COUNT 0)
(repeat SSL
	(setq SSN (ssname S1 COUNT))
	(setq ENA (entget SSN))
			(setq ASS2 (assoc 10 ENA))
			(setq P1 (cdr ASS2))
			(setq SSM (entnext SSN))
			(setq ENB (entget SSM))
	(if (= "ATTRIB" (DXF 0 ENB))(progn
			(setq ASS1 (assoc 1 ENB))
			(setq PZ1 (cdr ASS1))
			(setq PZ1 (atof PZ1))
			(if (/= PZ1 NIL)(progn
			(setq PX1 (car P1))
			(setq PY1 (cadr P1))
			(setq POINT1 (list PX1 PY1 PZ1))
			(setq ENB (subst (cons 10 (list (car (dxf 10 ENB))(cadr (dxf 10 ENB)) PZ1))(cons 10 (dxf 10 ENB)) ENB))
			(setq ENB (entmod ENB))
			))
			(setq ENA (subst (cons 10 (list (car (dxf 10 ENA))(cadr (dxf 10 ENA)) PZ1))(cons 10 (dxf 10 ENA)) ENA))
			(setq ENA (entmod ENA))
			(setq SSN (ENTUPD SSN))
			))
		(setq PX1 (car P1))
		(setq PX1 (rtos PX1 2 3))
		(setq PY1 (cadr P1))
		(setq PY1 (rtos PY1 2 3))
		(princ PN FD)(princ "\t\t" FD)(princ PX1 FD)(princ "\t" FD)(princ PY1 FD)(princ "\t" FD)(princ PZ1 FD)
		(princ "\n" FD)
		(setq PN (1+ PN))
(setq COUNT (1+ COUNT))
)
(close FD)
(SETQ PN NIL)

(princ)
)
