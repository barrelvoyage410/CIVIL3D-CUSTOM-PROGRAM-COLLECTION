(prompt"\nLoading EXPLODE.LSP...")
(defun EXPLODE ( / ES EG)
 (setvar "flatland" 0)
 (setq ES (entsel"\nSelect block, polyline, dimension, or mesh:")
       EG (entget(car ES))
 )
 (if(=(cdr(assoc 0 EG)) "INSERT")
  (if(not(=(cdr(assoc 41 EG))(cdr(assoc 42 EG))(cdr(assoc 43 EG))))
   (entmod(setq EG (subst (cons 42 (cdr(assoc 41 EG))) (assoc 42 EG) EG)
                EG (subst (cons 43 (cdr(assoc 41 EG))) (assoc 43 EG) EG))
   )
  )
 )
 (command "explode" ES)
 (princ)
)
(prompt"Done.")
(princ)
