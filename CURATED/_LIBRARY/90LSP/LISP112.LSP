(defun c:lisp112 ()
  (setvar "regenmode" 1)
  (setvar "limcheck" 1)
  (command "viewres" "y" "2000")
  (setq limm (list (+ (car (getvar "limmin")) 0.001) (+ (cadr
      (getvar "limmin")) 0.001)))
  (setq limax (list (- (car (getvar "limmax")) 0.001) (- (cadr
      (getvar "limmax")) 0.001)))
  (setq orxa (car (getvar "limmin")))
  (setq orya (cadr (getvar "limmin")))
  (setq orx (car limm))
  (setq ory (cadr limm))
  (setq x (+ orxa (car limax)))
  (setq y (+ orya (cadr limax)))
  (setq ofx (/ x 8))
  (setq ofy (/ y 8))
  (setq v10 (list orx y))
  (setq v1b (list (* x 0.25) y))
  (setq v2b (list (* x 0.5) y))
  (setq v3b (list (* x 0.75) y))
  (setq v4b (list x y))
  (setq v1a (list orx (* y 0.75)))
  (setq v2a (list (* x 0.25) (* y 0.75)))
  (setq v3a (list (* x 0.5) (* y 0.75)))
  (setq v4a (list (* x 0.75) (* y 0.75)))
  (setq v8b (list x (* y 0.75)))
  (setq v5a (list orx (* y 0.5)))
  (setq v6a (list (* x 0.25) (* y 0.5)))
  (setq v7a (list (* x 0.5) (* y 0.5)))
  (setq v8a (list (* x 0.75) (* y 0.5)))
  (setq v12b (list x (* y 0.5)))
  (setq v9a (list orx (* y 0.25)))
  (setq v10a (list (* x 0.25) (* y 0.25)))
  (setq v11a (list (* x 0.5) (* y 0.25)))
  (setq v12a (list (* x 0.75) (* y 0.25)))
  (setq v16b (list x (* y 0.25)))
  (setq v13a (list orx ory))
  (setq v14a (list (* x 0.25) ory))
  (setq v15a (list (* x 0.5) ory))
  (setq v16a (list (* x 0.75) ory))
  (setq v160 (list x ory))
  (setq vx (list orx ory))
  (setq vy (list x y))
  (setq sty (getvar "textstyle"))
  (setq crla (getvar "clayer"))
  (setq crcol (getvar "cecolor"))
  (command "layer" "m" "zoomlin" "c" "yellow" "zoomlin" "")
  (setq a (ssget "x" '((8 . "zoomlin"))))
  (command "erase" "p" "")
  (command "view" "w" "v1" v1a v1b)
  (command "view" "w" "v2" v2a v2b)
  (command "view" "w" "v3" v3a v3b)
  (command "view" "w" "v4" v4a v4b)
  (command "view" "w" "v5" v5a v2a)
  (command "view" "w" "v6" v6a v3a)
  (command "view" "w" "v7" v7a v4a)
  (command "view" "w" "v8" v8a v8b)
  (command "view" "w" "v9" v9a v6a)
  (command "view" "w" "v10" v10a v7a)
  (command "view" "w" "v11" v11a v8a)
  (command "view" "w" "v12" v12a v12b)
  (command "view" "w" "v13" v13a v10a)
  (command "view" "w" "v14" v14a v11a)
  (command "view" "w" "v15" v15a v12a)
  (command "view" "w" "v16" v16a v16b)
  (command "view" "w" "v0" vx vy)
  (command "view" "w" "v1q" v5a v2b)
  (command "view" "w" "v2q" v7a v4b)
  (command "view" "w" "v3q" v13a v7a)
  (command "view" "w" "v4q" v15a v12b)
  (command "line" v10 v4b "")
  (command "line" v1a v8b "")
  (command "line" v5a v12b "")
  (command "line" v9a v16b "")
  (command "line" v13a v160 "")
  (command "line" v10 v13a "")
  (command "line" v1b v14a "")
  (command "line" v2b v15a "")
  (command "line" v3b v16a "")
  (command "line" v4b v160 "")
  (command "id" (list (+ (car v1a) ofx) (+ (cadr v1a) ofy)))
  (command "text" "s" "standard" "m" "@" (/ ofx 2) "0" "1")
  (command "id" (list (+ (car v2a) ofx) (+ (cadr v2a) ofy)))
  (command "text" "m" "@" (/ ofx 2) "0" "2")
  (command "id" (list (+ (car v3a) ofx) (+ (cadr v3a) ofy)))
  (command "text" "m" "@" (/ ofx 2) "0" "3")
  (command "id" (list (+ (car v4a) ofx) (+ (cadr v4a) ofy)))
  (command "text" "s" "standard" "m" "@" (/ ofx 2) "0" "4")
  (command "id" (list (+ (car v5a) ofx) (+ (cadr v5a) ofy)))
  (command "text" "m" "@" (/ ofx 2) "0" "5")
  (command "id" (list (+ (car v6a) ofx) (+ (cadr v6a) ofy)))
  (command "text" "m" "@" (/ ofx 2) "0" "6")
  (command "id" (list (+ (car v7a) ofx) (+ (cadr v7a) ofy)))
  (command "text" "s" "standard" "m" "@" (/ ofx 2) "0" "7")
  (command "id" (list (+ (car v8a) ofx) (+ (cadr v8a) ofy)))
  (command "text" "m" "@" (/ ofx 2) "0" "8")
  (command "id" (list (+ (car v9a) ofx) (+ (cadr v9a) ofy)))
  (command "text" "m" "@" (/ ofx 2) "0" "9")
  (command "id" (list (+ (car v10a) ofx) (+ (cadr v10a) ofy)))
  (command "text" "s" "standard" "m" "@" (/ ofx 2) "0" "10")
  (command "id" (list (+ (car v11a) ofx) (+ (cadr v11a) ofy)))
  (command "text" "m" "@" (/ ofx 2) "0" "11")
  (command "id" (list (+ (car v12a) ofx) (+ (cadr v12a) ofy)))
  (command "text" "m" "@" (/ ofx 2) "0" "12")
  (command "id" (list (+ (car v13a) ofx) (+ (cadr v13a) ofy)))
  (command "text" "s" "standard" "m" "@" (/ ofx 2) "0" "13")
  (command "id" (list (+ (car v14a) ofx) (+ (cadr v14a) ofy)))
  (command "text" "m" "@" (/ ofx 2) "0" "14")
  (command "id" (list (+ (car v15a) ofx) (+ (cadr v15a) ofy)))
  (command "text" "m" "@" (/ ofx 2) "0" "15")
  (command "id" (list (+ (car v16a) ofx) (+ (cadr v16a) ofy)))
  (command "text" "s" "standard" "m" "@" (/ ofx 2) "0" "16")
  (command "layer" "s" crla "")
  (command "color" crcol)
  (command "style" sty "" "" "" "" "" "" "")
  (command "view" "r" "v0")
  (setvar "regenmode" 0)
)
