(defun c:lisp123 (/ e pt1 e2 e1)
  (prompt "\nPick arc  ")
  (setq e (entsel))
  (setq pt1 (cadr e))
  (setq e2 (car e))
  (setq e1 (entget (car e)))
  (if (= (cdr (assoc 0 e1)) "POLYLINE") (command "explode" e2))
  (command "pedit" pt1 "y" "")
  (command "area" "e" pt1)
  (command "explode" pt1)
  (princ "\n  ") (princ "\n  ")
  (princ "\nLength:  ")
  (princ (getvar "perimeter"))
  (princ)
)
