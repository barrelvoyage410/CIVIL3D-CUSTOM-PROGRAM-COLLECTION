(DEFUN  C:ISOLATE(/  QOQ Q@Q)(SETQ  QOQ(SSGET "P")Q@Q 0)(IF  QOQ(PROGN (GRCLEAR )(REPEAT (SSLENGTH  QOQ)(REDRAW (SSNAME  QOQ Q@Q))(SETQ  Q@Q(1+  Q@Q)))))(PROMPT (STRCAT "\nIsolated "(ITOA  Q@Q)))(PRIN1 ))
