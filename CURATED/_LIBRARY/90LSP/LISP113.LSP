(defun c:z0 ()
  (command "'view" "r" "v0"))
(defun c:z1 ()
  (command "'view" "r" "v1"))
(defun c:z2 ()
  (command "'view" "r" "v2"))
(defun c:z3 ()
  (command "'view" "r" "v3"))
(defun c:z4 ()
  (command "'view" "r" "v4"))
(defun c:z5 ()
  (command "'view" "r" "v5"))
(defun c:z6 ()
  (command "'view" "r" "v6"))
(defun c:z7 ()
  (command "'view" "r" "v7"))
(defun c:z8 ()
  (command "'view" "r" "v8"))
(defun c:z9 ()
  (command "'view" "r" "v9"))
(defun c:z10 ()
  (command "'view" "r" "v10"))
(defun c:z11 ()
  (command "'view" "r" "v11"))
(defun c:z12 ()
  (command "'view" "r" "v12"))
(defun c:z13 ()
  (command "'view" "r" "v13"))
(defun c:z14 ()
  (command "'view" "r" "v14"))
(defun c:z15 ()
  (command "'view" "r" "v15"))
(defun c:z16 ()
  (command "'view" "r" "v16"))
(defun c:z1q ()
  (command "'view" "r" "v1q"))
(defun c:z2q ()
  (command "'view" "r" "v2q"))
(defun c:z3q ()
  (command "'view" "r" "v3q"))
(defun c:z4q ()
  (command "'view" "r" "v4q"))
