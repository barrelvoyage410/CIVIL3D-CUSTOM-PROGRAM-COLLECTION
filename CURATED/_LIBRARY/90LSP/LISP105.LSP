(defun c:lisp105 ()
  (setq os (getvar "osmode"))
  (setvar "osmode" 512)
  (setq pt2 (getpoint "\nPick one of the arcs  "))
  (setq a (entget (ssname (ssget pt2) 0)))
  (setq pt1 (cdr (assoc 10 a)))
  (setq ra (cdr (assoc 40 a)))
  (command "erase" pt2 "")
  (setq pt3 (getpoint "\nPick other arc  "))
  (setvar "osmode" os)
  (command "erase" pt3 "")
  (command "circle" pt1 ra)
)
