(princ)
(prompt "\nEnd.lsp...by Kent Keller")
(princ)
(setvar "cmdecho" 0)
(command "undefine" "end")
(setvar "cmdecho" 1)
(defun c:end ()
   (setvar "cmdecho" 0)
   (setq NAME
      (strcat (getvar "dwgprefix")
           (getvar "dwgname")
      )
   )

   (prompt "\nEnter Name of Drawing to WBlock <")
   (prompt NAME)
   (if (/= (setq NEWNAM
                (getstring ">: ")
           )
           ""
       )
       (setq NAME NEWNAM)
   )
   (prin1)
   (prompt "\nSaving original and writing backup file.")
   (command "save" "")
   (command "shell" (strcat "copy " name ".dwg *.bak"))
   (command "shell" (strcat "del " name ".dwg"))
          (command "wblock" name "*")
   (prompt "\nEnding drawing")
   (command "quit" "y")
)
(prin1)
