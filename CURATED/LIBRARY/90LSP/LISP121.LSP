(defun rtd (angg)
  (/ (* angg 180.0) pi))
(defun c:lisp121 (/ fln sty pt1 hgt rot f e txt)
  (setq fln (getstring "\nFile name to import  "))
  (setq sty (getstring "\nEnter text STYLE or <ENTER> for existing style  "))
  (setq pt1 (getpoint "\nPick beginning point of text  "))
  (setq f (open fln "r"))
  (if (/= sty "") (command "text" "style" sty ^c))
  (setq st (getvar "textstyle"))
  (setq e (tblsearch "style" st))
  (setq tsize (cdr (assoc 40 e)))
  (if (/= tsize 0) (setq hgt nil))
  (if (= tsize 0)
      (setq hgt (getdist pt1 "\nHeight  ")))
  (setq rot (getangle "\nText rotation  "))
  (if (= rot nil) (setq rot 0))
  (setq rot (rtd rot))
  (setq txt (read-line f))
  (if (= hgt nil) (command "text" pt1 rot txt))
  (if (/= hgt nil) (command "text" pt1 hgt rot txt))
  (setq e 1)
  (while e
    (setq txt (read-line f))
    (if (= txt nil) (setq e nil))
    (if (= hgt nil) (command "text" "" txt))
    (if (/= hgt nil) (command "text" "" txt))
  )
  (close f)
)
