(VMON )(SETVAR "CMDECHO"0)(PROMPT "\n Global Utilities ")(SETQ  !GU-LST(quote ("AUTOJOIN""CBLOCK""CDIA""CHKBLK""COUNT""CPLINE""CSTYLE""FINDMIR""FTEXT""HTEXT""ISOLATE""JOINCHK""LCLEAN""LX""MERGE""PART""PCOUNT""RESET""ROUND""RTEXT""SSGET""TEXTADD""WIDTH""WPART""XBLOCK""XPLINE")))(SETQ  Q# !GU-LST)(WHILE (SETQ  QLQ(CAR  Q#))(EVAL (LIST (quote DEFUN )(READ (STRCAT "C:"QLQ))(quote ())(LIST (quote Q1QL)!GU-PATH QLQ)(LIST (READ (STRCAT "C:"QLQ)))))(SETQ  Q#(CDR  Q#)))(IF (= (LOAD (STRCAT  !GU-PATH"UTIL")"NOT")"NOT")(PROMPT (STRCAT "\n File "!GU-PATH"UTIL.LSP not found. "))(DEFUN  C:GU(/  Q1Q)(IF (/= (CADDR  *ERROR* )"UTIL")(DEFUN  *ERROR* (Q?J)"UTIL"(PROMPT (STRCAT "ERROR: "Q?J))(IF  !DEICE(Q&))(GRTEXT )(PRIN1 )))(PROMPT (IF  !GU-CMD(STRCAT "Command <"!GU-CMD">: ")"GU Command: "))(IF (SETQ  Q1Q(Q&@L !GU-LST))(IF (=  Q1Q"default")(IF  !GU-CMD(EVAL (LIST (READ (STRCAT "C:"!GU-CMD)))))(PROGN (EVAL (LIST (READ (STRCAT "C:"Q1Q))))(SETQ  !GU-CMD Q1Q))))(PRIN1 )))(DEFUN  Q#Q(FILE )(COND ((GETENV "COMSPEC")(COMMAND "SH"(STRCAT "DIR/P "FILE )))((GETENV "USER")(COMMAND "SH"(STRCAT "ls "FILE )))))(DEFUN  QQL(QQQ Q# /  QLL)(WHILE  Q#(IF (/= (CAR  Q#)QQQ)(SETQ  QLL(CONS (CAR  Q#)QLL)))(SETQ  Q#(CDR  Q#)))(REVERSE  QLL))(DEFUN  Q%L(Q&Q /  QLJ Q#)(SETQ  QLJ(CDR (ASSOC  2(TBLNEXT  Q&Q T ))))(WHILE  QLJ(SETQ  Q#(APPEND  Q#(LIST  QLJ)))(SETQ  QLJ(CDR (ASSOC  2(TBLNEXT  Q&Q)))))Q#)(DEFUN  QL1(QJ& Q&1)(IF (=  Q&1 0)(ATOI (RTOS  QJ& 2 Q&1))(ATOF (RTOS  QJ& 2 Q&1))))(DEFUN  QJ#(QJ@ Q@#)(LIST (ATOF (RTOS (CAR  QJ@)2 Q@#))(ATOF (RTOS (CADR  QJ@)2 Q@#))))(DEFUN  QQ#(Q0@ QO1)(IF (AND (EQUAL (CAR  Q0@)(CAR  QO1)0.0001)(EQUAL (CADR  Q0@)(CADR  QO1)0.0001))T  NIL))(DEFUN  Q11(Q#1 Q#)(CDR (ASSOC  Q#1 Q#)))(DEFUN  Q|Q(/  Q0&)(COMMAND "POINT""0,0")(SETQ  Q0&(ENTLAST ))(ENTDEL (ENTLAST ))Q0&)(DEFUN  Q%Q(Q$& /  QOQ Q1&)(SETQ  QOQ(SSADD ))(SETQ  Q1&(ENTNEXT  Q$&))(WHILE  Q1&(SSADD  Q1& QOQ)(SETQ  Q1&(ENTNEXT  Q1&)))QOQ)(DEFUN  Q?Q(FILE  /  QJQ Q@Q QQQ QLQ)(SETQ  QJQ(STRLEN  FILE )Q@Q 1)(REPEAT  QJQ(SETQ  QQQ(SUBSTR  FILE  Q@Q 1)Q@Q(1+  Q@Q))(IF (OR (=  QQQ"/")(=  QQQ"\\"))(SETQ  QLQ Q@Q)))(IF  QLQ(SUBSTR  FILE  QLQ)FILE ))(DEFUN  Q&J(STR  QO% /  Q@Q Q$% QQJ Q|% Q%% Q??J QJ?J Q?| Q@?J QQ?J QL?J Q&?J Q@| Q1?J Q#?J)(SETQ  STR (STRCASE  STR )Q@Q 1)(REPEAT (STRLEN  STR )(SETQ  Q$%(SUBSTR  STR  Q@Q 1))(IF (=  Q$%",")(SETQ  Q|%(CONS  QQJ Q|%)QQJ NIL)(SETQ  QQJ(IF  QQJ(STRCAT  QQJ Q$%)Q$%)))(SETQ  Q@Q(1+  Q@Q)))(SETQ  Q|%(CONS  QQJ Q|%)Q%%(LENGTH  Q|%))(WHILE (SETQ  Q??J(CAR  QO%))(SETQ  Q@Q 0 Q?| T  QJ?J(STRLEN  Q??J)Q@?J NIL)(WHILE (AND  Q?|(<  Q@Q Q%%))(SETQ  QQ?J(NTH  Q@Q Q|%)QL?J(STRLEN  QQ?J)Q&?J 1 Q@| T  Q1?J T )(WHILE  Q@|(SETQ  Q$%(SUBSTR  QQ?J Q&?J 1))(COND ((=  Q$%"*")(SETQ  Q@| NIL))((=  Q$%"?")NIL)((/=  Q$%(SUBSTR  Q??J Q&?J 1))(SETQ  Q@| NIL Q1?J NIL)))(SETQ  Q&?J(1+  Q&?J))(IF (AND  Q@|(>  Q&?J QL?J))(SETQ  Q@| NIL Q1?J(IF (/=  QJ?J QL?J)NIL T ))))(IF  Q1?J(SETQ  Q?| NIL Q@?J T )(SETQ  Q@Q(1+  Q@Q))))(IF  Q@?J(SETQ  Q#?J(CONS  Q??J Q#?J)))(SETQ  QO%(CDR  QO%)))(REVERSE  Q#?J))(DEFUN  Q|1(Q0@ QO1)(LIST (- (CAR  Q0@)(CAR  QO1))(- (CADR  Q0@)(CADR  QO1))))(DEFUN  Q?#(QJ@ Q@@)(LIST (* (CAR  QJ@)Q@@)(* (CADR  QJ@)Q@@)))(DEFUN  Q@0(QOQ QJ@ /  Q@L Q&0 Q10 Q#0)(SETQ  Q@L T )(WHILE  Q@L(INITGET "Move Rotate")(SETQ  Q&0(GETPOINT  QJ@"\nMove/Rotate/<Second point of displacement>: "))(COND ((= (TYPE  Q&0)(quote LIST ))(SETQ  Q10(ENTLAST ))(COMMAND "COPY"QOQ""QJ@ Q&0)(SETQ  QOQ(SSADD ))(SETQ  Q#0(ENTNEXT  Q10))(WHILE  Q#0(SSADD  Q#0 QOQ)(SETQ  Q#0(ENTNEXT  Q#0)))(SETQ  QJ@(GETVAR "LASTPOINT")))((=  Q&0"Move")(PROMPT "New point: ")(COMMAND "MOVE"QOQ""QJ@ PAUSE )(SETQ  QJ@(GETVAR "LASTPOINT")))((=  Q&0"Rotate")(PROMPT "Angle: ")(COMMAND "ROTATE"QOQ""QJ@ PAUSE ))((=  Q&0 NIL)(SETQ  Q@L NIL)))))(C:GU)
