(defun c:lisp118 (/ k a b1 th onoff th1 onoff1)
  (textscr)
  (setq k 5)
  (setq a nil)
  (princ "\nLayers                    Status")(terpri)(terpri)
  (while (setq b1 (tblnext "layer" k))
    (setq k nil)
    (setq th (assoc 70 b1))
    (setq onoff (assoc 62 b1))
    (setq th1 (cdr th))
    (setq onoff1 (cdr onoff))
    (if (or (= th1 65) (= th1 1))
      (progn
        (setq a 5)
        (princ (cdr (assoc 2 b1)))
        (princ "                         ") (princ "Frozen")
        (terpri)
      )
    )
    (if (< onoff1 0)
      (progn
        (setq a 5)
        (princ (cdr (assoc 2 b1)))
        (princ "                         ") (princ "Off")
        (terpri)
      )
    )
  )
  (if (= a nil)
    (prompt "There are no Frozen or Off layers in the database
\n")
  )
  (prin1)
)
