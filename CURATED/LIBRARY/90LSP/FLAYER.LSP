(defun c:layman ()
(reset_cmd)
(WHILE (NULL(SETQ ENT (CAR (ENTSEL "\nSelect Entity:"))))(alert "Nothing Selected!"))
(setq entdat (entget ent))
(setq lay (cdr(assoc 8 entdat)))
(prompt "\nSelected Layer: ")
(princ lay)
(initget  "F O D C")
(setq ans(getkword "\nFreeze/Off/Delete/Current:"))
 (cond ((= (strcase ans) "F") (f_layer lay))
       ((= (strcase ans) "O") (O_layer lay))
       ((= (strcase ans) "D") (D_layer lay))
       ((= (strcase ans) "C") (C_layer lay))
 )
(princ)
)

(defun f_layer (lay)
(command "layer" "f" lay "")
)

(defun o_layer (lay)
(command "layer" "off" lay "" "")
)

(defun d_layer (lay)
(initget 1 "Y N")
(PROMPT "\nThis will Delete all entities on layer ")
(setq ans (getkword (strcat lay"! Continue <Y/N>")))
(if (= (strcase ans) "Y")
(progn
(setq elist (ssget "X" (list (cons 8 lay))))
(setq l 0)
(repeat (sslength elist)
(entdel (ssname elist l))
(setq l (1+ l))
)
)
)
)

(defun c_layer (lay)
(command "layer" "s" lay "")
)
(defun reset_cmd ()
(command "undo" "m")
(if (getvar "cmddia") (setq dia 1))
(setvar "cmddia" 1)
)

(prompt "\nLAYMAN V1.00")
(prompt "\nType LAYMAN to start.")
(prompt "\nBy Dyanmic Enterprises..")
(prompt "\ncopyright 1993")
(setq n 0)
