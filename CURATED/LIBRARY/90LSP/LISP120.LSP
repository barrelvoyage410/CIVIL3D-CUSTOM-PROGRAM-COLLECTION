(defun c:lisp120 (/ blm os pt1 sty e tsize siz arc txt r len dia hf int ang cnt ss nang pt tr)
  (setq blm (getvar "blipmode"))
  (setvar "blipmode" 0)
  (setq os (getvar "osmode"))
  (setq pt1 (getpoint  "\nBeginning point of text  "))
  (setq sty (getvar "textstyle"))
  (setq e (tblsearch "style" sty))
  (setq tsize (cdr (assoc 40 e)))
  (setq siz tsize)
  (if (= tsize 0)
    (setq siz (getdist pt1  "\nText height  ")))
  (setvar "osmode" 4)
  (setq arc (getpoint  "\nPick the arc  "))
  (setvar "osmode" os)
  (setq txt (getstring 1 "\nText:  "))
  (setq r (distance arc pt1))
  (setq len (strlen txt))
  (setq dia (* (/ (* siz len) (* 2.0 pi r)) 360.0))
  (setq hf (/ (* dia pi) 180.0))
  (setq int (/ hf len))
  (setq ang (angle arc pt1))
  (setq cnt 0)
  (setq ss (ssadd))
  (while (< cnt len)
  (setq nang (- ang (* cnt int)))
    (setq pt (polar arc nang (+ r (/ siz 2.0))))
    (setq tr (- (/ (* 180.0 nang) pi) 90.0))
    (setq cnt (+ cnt 1))
    (if (= tsize 0)
      (command "text" "c" pt siz tr (substr txt cnt 1))
      (command "text" "c" pt tr (substr txt cnt 1)))
    (setq ss (ssadd (entlast) ss))
  )
  (setvar "blipmode" blm)
  (princ)
)
