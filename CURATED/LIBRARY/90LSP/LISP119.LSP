(defun c:lisp119 (/ k a b1 th onoff th1 onoff1)
  (setq p (open "prn" "w"))
  (princ "           " p)
  (princ "Review of Off or Frozen Layers in the Database\n" p)
  (princ "\n\n" p)
  (setq k 5)
  (setq a nil)
  (princ "Layers                    Status\n\n" p)
  (while (setq b1 (tblnext "layer" k))
    (setq k nil)
    (setq th (assoc 70 b1))
    (setq onoff (assoc 62 b1))
    (setq th1 (cdr th))
    (setq onoff1 (cdr onoff))
    (if (or (= th1 65) (= th 1))
      (progn
        (setq a 5)
        (princ (cdr (assoc 2 b1)) p)
        (princ "                         " p) (princ "Frozen\n"
p)
      )
    )
    (if (< onoff1 0)
      (progn
        (setq a 5)
        (princ (cdr (assoc 2 b1)) p)
        (princ "                         " p) (princ "Off\n" p)
      )
    )
  )
  (if (= a nil)
    (prompt "There are no Frozen or Off layers in the database
\n" p)
  )
  (princ (chr 12) p)
  (close p)
  (prin1)
)
