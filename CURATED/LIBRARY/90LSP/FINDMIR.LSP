(DEFUN  C:FINDMIR(/  QL% Q@Q QO& QJQ Q&% Q1& Q#&)(Q@)(PROMPT "\nWorking on it. ")(SETQ  QL%(SSGET "X"(LIST (CONS  0"INSERT"))))(SETQ  Q@Q 0 QO& 0)(IF  QL%(PROGN (SETQ  QJQ(SSLENGTH  QL%))(GRCLEAR ))(SETQ  QJQ 0))(SETQ  Q&%(SSADD ))(REPEAT  QJQ(SETQ  Q#&(ENTGET (SETQ  Q1&(SSNAME  QL% Q@Q))))(IF (< (CDR (ASSOC  41 Q#&))0)(PROGN (REDRAW  Q1&)(SSADD  Q1& Q&%)(SETQ  QO&(1+  QO&))))(SETQ  Q@Q(1+  Q@Q)))(PROMPT (STRCAT "\nFound "(ITOA  QO&)))(IF (>  QO& 0)(PROGN (INITGET "Y N")(IF (= (GETKWORD "\nDo you want mirrored blocks unmirrored? <N>: ")"Y")(PROGN (SETQ  Q@Q 0)(REPEAT (SSLENGTH  Q&%)(SETQ  Q#&(ENTGET (SETQ  Q1&(SSNAME  Q&% Q@Q))))(ENTMOD (SUBST (CONS  41(ABS (CDR (ASSOC  41 Q#&))))(ASSOC  41 Q#&)Q#&))(SETQ  Q@Q(1+  Q@Q))))))(REDRAW ))(Q&))
