(defun c:lisp102 ()
  (setq os (getvar "osmode"))
  (setvar "osmode" 512)
  (setq pt1 (getpoint "\nPick block  "))
  (setvar "osmode" os)
  (setq a (ssname (ssget pt1) 0))
  (setq e (entget a))
  (setq pt1 (cdr (assoc 10 e)))
  (command "copy" a "" pt1 pt1)
  (command "erase" "last" "")
  (redraw a 1)
  (command "explode" a)
  (princ "\n  ") (princ "\n  ")
  (prompt "\nSelect objects to be mirrored  ")
  (setq sss (ssget))
  (command "mirror" sss "" pause pause "Y")
  (command "oops")
)
