(defun c:INSERTM ()
  (setvar "cmdecho" 0)
  (if (= XSF nil) (setq XSF 1.0))
  (if (= YSF nil) (setq YSF 1.0))
  (if (= RTA nil) (setq RTA 0.0))
  (if BLK
   (progn
    (setq TYP (strcat "\nBlock to Insert: <" BLK "> "))
    (setq BLK (if (= (setq CTP (getstring TYP)) "") BLK CTP))
   )
   (setq BLK (getstring "\nBlock to Insert: "))
  )
  (setq XS (rtos XSF 2 2))
  (setq XSS (strcat "\nX Scale Factor: <" XS "> "))
  (setq SFX (atof (getstring XSS)))
  (if (/= SFX 0.0) (setq XSF SFX))
  (setq YS (rtos YSF 2 2))
  (setq YSS (strcat "\nY Scale Factor: <" YS "> "))
  (setq SFY (atof (getstring YSS)))
  (if (/= SFY 0.0) (setq YSF SFY))
  (setq RA (rtos RTA 2 2))
  (setq RAS (strcat "\nRotation Angle: <" RA "> "))
  (setq ATR (atof (getstring RAS)))
  (if (/= ATR 0.0) (setq RTA ATR))
  (setq IPT (getpoint "Insertion point: "))
  (command "INSERT" BLK IPT XSF YSF RTA "")
  (command "COPY" "L" "" "M" IPT)
)
