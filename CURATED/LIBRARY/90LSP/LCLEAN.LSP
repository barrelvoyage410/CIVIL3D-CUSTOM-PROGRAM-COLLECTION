(DEFUN  C:LCLEAN(/  Q&Q QOL Q#&Q Q?%J Q0L QOQ QL% Q&% Q1& Q&Q)(Q@)(REPEAT  20(PRINT ))(TEXTSCR )(SETQ  Q&Q(GETVAR "CELTYPE")QOL(GETVAR "CLAYER")Q#&Q(GETVAR "ELEVATION")Q?%J(GETVAR "THICKNESS")Q0L(GETVAR "CECOLOR"))(PROMPT "\nSelected lines and arcs will change to these current property settings.")(PRINT )(PROMPT (STRCAT "\n   Layer     "QOL))(PROMPT (STRCAT "\n   Color     "Q0L))(PROMPT (STRCAT "\n   Linetype  "Q&Q))(PROMPT (STRCAT "\n   Elevation "(RTOS  Q#&Q 2 3)))(PROMPT (STRCAT "\n   Thickness "(RTOS  Q?%J 2 3)))(REPEAT  5(PRINT ))(INITGET "Y N")(IF (/= (GETKWORD "\nContinue? <Y>: ")"N")(PROGN (SETQ  QOQ(SSGET )QL%(SSADD )Q&%(SSADD ))(WHILE (SETQ  Q1&(SSNAME  QOQ 0))(SETQ  Q&Q(CDR (ASSOC  0(ENTGET  Q1&))))(COND ((=  Q&Q"LINE")(SSADD  Q1& QL%))((=  Q&Q"ARC")(SSADD  Q1& Q&%)))(SSDEL  Q1& QOQ))(IF (> (SSLENGTH  QL%)0)(Q0&Q QL%)(PROMPT "\nNumber of arcs found - 0"))(IF (> (SSLENGTH  Q&%)0)(Q$&Q Q&%)(PROMPT "\nNumber of arcs found - 0"))))(Q&))(DEFUN  Q$&Q(QOQ /  Q1@J Q@Q QO& Q1& Q#& Q%# Q$JJ QOLQ Q|LQ QO% Q?| Q|% Q#?J Q%LQ Q?&Q)(SETQ  Q1@J(SSLENGTH  QOQ)Q@Q 0)(SETQ  QO& Q1@J)(PROMPT "\nNumber of arcs found - ")(PRIN1  QO&)(PROMPT "  Need to process - ")(SETQ  Q#&(ENTGET (SETQ  Q1&(SSNAME  QOQ 0)))Q%#(CDR (ASSOC  10 Q#&))Q$JJ(CDR (ASSOC  40 Q#&))QOLQ(CDR (ASSOC  50 Q#&))Q|LQ(CDR (ASSOC  51 Q#&)))(IF (>  QOLQ Q|LQ)(SETQ  QOLQ(-  QOLQ(*  PI  2))))(SETQ  QO%(LIST (LIST  Q%# Q$JJ QOLQ Q|LQ)))(SSDEL  Q1& QOQ)(ENTDEL  Q1&)(SETQ  QO&(1-  QO&))(WHILE (SETQ  Q1&(SSNAME  QOQ 0))(PRIN1  QO&)(SETQ  Q#&(ENTGET  Q1&)Q?| T  Q%#(CDR (ASSOC  10 Q#&))Q$JJ(CDR (ASSOC  40 Q#&))QOLQ(CDR (ASSOC  50 Q#&))Q|LQ(CDR (ASSOC  51 Q#&)))(IF (>  QOLQ Q|LQ)(SETQ  QOLQ(-  QOLQ(*  PI  2))))(ENTDEL  Q1&)(WHILE  Q?|(IF  QO%(PROGN (SETQ  Q|%(CAR  QO%)QO%(CDR  QO%))(IF (AND (EQUAL (CAR  Q|%)Q%# 0.001)(EQUAL (CADR  Q|%)Q$JJ 0.001))(PROGN (SETQ  Q%LQ(NTH  2 Q|%)Q?&Q(NTH  3 Q|%))(IF (AND (>=  QOLQ Q%LQ)(<=  QOLQ Q?&Q))(SETQ  QOLQ Q%LQ Q?| NIL))(IF (AND (>=  Q|LQ Q%LQ)(<=  Q|LQ Q?&Q))(SETQ  Q|LQ Q?&Q Q?| NIL))(IF  Q?|(IF (AND (>=  Q%LQ QOLQ)(<=  Q%LQ Q|LQ))(SETQ  Q?| NIL)))))(IF  Q?|(SETQ  Q#?J(CONS  Q|% Q#?J))(SETQ  QO%(APPEND (CONS (LIST  Q%# Q$JJ QOLQ Q|LQ)Q#?J)QO%)Q@Q(1+  Q@Q))))(SETQ  QO%(CONS (LIST  Q%# Q$JJ QOLQ Q|LQ)Q#?J)Q?| NIL)))(SETQ  Q#?J NIL)(REPEAT (STRLEN (ITOA  QO&))(PRINC (CHR  8)))(SETQ  QO&(1-  QO&))(SSDEL  Q1& QOQ))(REPEAT  20(PRINC (CHR  8)))(PROMPT "  Eliminated - ")(PRIN1  Q@Q)(WHILE  QO%(SETQ  Q|%(CAR  QO%)Q%#(NTH  0 Q|%)Q$JJ(NTH  1 Q|%))(COMMAND "ARC"(POLAR  Q%#(NTH  2 Q|%)Q$JJ)"C"Q%#(POLAR  Q%#(NTH  3 Q|%)Q$JJ))(SETQ  QO%(CDR  QO%))))(DEFUN  Q0&Q(QOQ /  Q1@J Q@Q QO& Q1& Q#& Q0@ QO1 QO&Q QO% Q?| QLQ Q&| Q|% Q#?J Q@| Q$# QO# Q|&Q Q$| Q1#J Q%&Q Q?1Q)(SETQ  Q1@J(SSLENGTH  QOQ)Q@Q 0)(SETQ  QO& Q1@J)(PROMPT "\nNumber of lines found - ")(PRIN1  QO&)(PROMPT "  Need to process - ")(SETQ  Q#&(ENTGET (SETQ  Q1&(SSNAME  QOQ 0)))Q0@(CDR (ASSOC  10 Q#&))QO1(CDR (ASSOC  11 Q#&)))(SETQ  QO&Q(QJ1Q Q0@ QO1)QO%(IF (>=  QO&Q 180)(LIST (LIST (-  QO&Q 180)(LIST  QO1 Q0@)))(LIST (LIST  QO&Q(LIST  Q0@ QO1)))))(SSDEL  Q1& QOQ)(ENTDEL  Q1&)(SETQ  QO&(1-  QO&))(WHILE (SETQ  Q1&(SSNAME  QOQ 0))(PRIN1  QO&)(SETQ  Q#&(ENTGET  Q1&)Q?| T  Q0@(CDR (ASSOC  10 Q#&))QO1(CDR (ASSOC  11 Q#&)))(IF (>= (QJ1Q Q0@ QO1)180)(SETQ  QLQ Q0@ Q0@ QO1 QO1 QLQ))(SETQ  QO&Q(QJ1Q Q0@ QO1)Q&| NIL)(ENTDEL  Q1&)(IF (< (DISTANCE  Q0@ QO1)0.001)(SETQ  Q?| NIL Q@Q(1+  Q@Q)))(WHILE  Q?|(IF  QO%(PROGN (SETQ  Q|%(CAR  QO%)QO%(CDR  QO%))(IF (= (CAR  Q|%)QO&Q)(PROGN (SETQ  QO&Q(CAR  Q|%)Q#?J(CDR  Q|%)Q@| T )(WHILE  Q@|(SETQ  Q?1Q(CAR  Q#?J)Q$#(CAR  Q?1Q)QO#(CADR  Q?1Q)Q|&Q(QJ1Q Q0@ Q$#)Q$|(DISTANCE  Q0@ QO1)Q1#J(DISTANCE  Q$# QO#))(COND ((EQUAL  Q0@ Q$# 0.001)(SETQ  QO1(POLAR  Q0@(Q|& QO&Q)(MAX  Q$| Q1#J))Q@Q(1+  Q@Q)Q@| NIL))((EQUAL  QO1 QO# 0.001)(SETQ  Q0@(POLAR  QO1(Q|&(+  QO&Q 180))(MAX  Q$| Q1#J))Q@Q(1+  Q@Q)Q@| NIL))((EQUAL  Q0@ QO# 0.001)(SETQ  Q0@ Q$# Q@Q(1+  Q@Q)Q@| NIL))((EQUAL  QO1 Q$# 0.001)(SETQ  QO1 QO# Q@Q(1+  Q@Q)Q@| NIL))((=  QO&Q(-  Q|&Q 180))(IF (< (DISTANCE  Q$# Q0@)Q1#J)(IF (< (+ (DISTANCE  Q$# Q0@)Q$|)Q1#J)(SETQ  Q0@ Q$# QO1 QO# Q@Q(1+  Q@Q)Q@| NIL)(SETQ  Q0@ Q$# Q@Q(1+  Q@Q)Q@| NIL))(SETQ  Q%&Q(APPEND (LIST  Q?1Q)Q%&Q))))((=  QO&Q Q|&Q)(IF (< (DISTANCE  Q0@ Q$#)Q$|)(IF (< (+ (DISTANCE  Q0@ Q$#)Q1#J)Q$|)(SETQ  Q@Q(1+  Q@Q)Q@| NIL)(SETQ  QO1 QO# Q@Q(1+  Q@Q)Q@| NIL))(SETQ  Q%&Q(APPEND (LIST  Q?1Q)Q%&Q))))(T (SETQ  Q%&Q(APPEND (LIST  Q?1Q)Q%&Q))))(SETQ  Q#?J(CDR  Q#?J))(IF  Q@|(IF (NOT  Q#?J)(SETQ  Q|%(CONS  QO&Q(CONS (LIST  Q0@ QO1)Q%&Q))Q@| NIL))(SETQ  Q|%(CONS  QO&Q(APPEND (CONS (LIST  Q0@ QO1)Q%&Q)Q#?J)))))(SETQ  QO%(CONS  Q|%(APPEND  Q&| QO%))Q?| NIL))(SETQ  Q&|(CONS  Q|% Q&|))))(SETQ  QO%(CONS (LIST  QO&Q(LIST  Q0@ QO1))Q&|)Q?| NIL))(SETQ  Q%&Q NIL))(REPEAT (STRLEN (ITOA  QO&))(PRINC (CHR  8)))(SETQ  QO&(1-  QO&))(SSDEL  Q1& QOQ))(REPEAT  20(PRINC (CHR  8)))(PROMPT "  Eliminated - ")(PRIN1  Q@Q)(WHILE (SETQ  Q|%(CAR  QO%))(SETQ  Q#?J(CDR  Q|%))(WHILE  Q#?J(SETQ  Q%&Q(CAR  Q#?J))(COMMAND "LINE"(CAR  Q%&Q)(CADR  Q%&Q)"")(SETQ  Q#?J(CDR  Q#?J)))(SETQ  QO%(CDR  QO%))))(DEFUN  QJ1Q(Q0@ QO1)(ATOI (ANGTOS (ANGLE  Q0@ QO1)0 0)))
