(DEFUN  C:HTEXT(/  Q&0 QOQ QLQ Q@Q Q1& QOQ Q#& Q$@ QL| Q&| QO& Q@@)(Q@)(COMMAND "UNDO""M")(INITGET "Global Selective")(SETQ  Q&0(GETKWORD "\nGlobal or Selective <S>: "))(IF (=  Q&0"Global")(SETQ  QOQ(SSGET "X"(LIST (CONS  0"TEXT"))))(PROGN (SETQ  QLQ(SSGET ))(IF  QLQ(PROGN (SETQ  Q@Q 0)(SETQ  Q1&(SSNAME  QLQ Q@Q))(SETQ  QOQ(SSADD ))(WHILE  Q1&(SETQ  Q#&(ENTGET  Q1&))(IF (= (CDR (ASSOC  0 Q#&))"TEXT")(SSADD  Q1& QOQ))(SETQ  Q@Q(1+  Q@Q))(SETQ  Q1&(SSNAME  QLQ Q@Q)))))))(IF (AND  QOQ(> (SSLENGTH  QOQ)0))(PROGN (INITGET  1"1 2 3")(SETQ  Q&0(GETKWORD "\n1= Scale all. 2= All to new. 3= Old to new: "))(SETQ  Q@Q 0 QO& 0)(COND ((=  Q&0"2")(INITGET  7)(SETQ  Q$@(GETREAL "\nNew height: "))(WHILE (SETQ  Q1&(SSNAME  QOQ Q@Q))(SETQ  Q#&(ENTGET  Q1&))(IF (NOT (EQUAL  Q$@(CDR (ASSOC  40 Q#&))0.0001))(PROGN (SETQ  Q#&(SUBST (CONS  40 Q$@)(ASSOC  40 Q#&)Q#&))(ENTMOD  Q#&)(SETQ  QO&(1+  QO&))))(SETQ  Q@Q(1+  Q@Q))))((=  Q&0"3")(INITGET  7)(SETQ  QL|(GETREAL "\nOld height: "))(INITGET  7)(SETQ  Q&|(GETREAL "\nNew height: "))(WHILE (SETQ  Q1&(SSNAME  QOQ Q@Q))(SETQ  Q#&(ENTGET  Q1&))(IF (EQUAL  QL|(CDR (ASSOC  40 Q#&))0.0001)(PROGN (SETQ  Q#&(SUBST (CONS  40 Q&|)(ASSOC  40 Q#&)Q#&))(ENTMOD  Q#&)(SETQ  QO&(1+  QO&))))(SETQ  Q@Q(1+  Q@Q))))((=  Q&0"1")(INITGET  7)(SETQ  Q@@(GETREAL "\nScale: "))(WHILE (SETQ  Q1&(SSNAME  QOQ Q@Q))(SETQ  Q#&(ENTGET  Q1&))(ENTMOD (SUBST (CONS  40(QL1(*  Q@@(CDR (ASSOC  40 Q#&)))3))(ASSOC  40 Q#&)Q#&))(SETQ  Q@Q(1+  Q@Q)))(SETQ  QO& Q@Q)))(PROMPT (STRCAT "\nChanged "(ITOA  QO&))))(PROMPT "\nNo text found. "))(Q&))
