(DEFUN  C:JOINCHK(/  QL% Q0#J Q#& Q#1J Q0@ QO1 Q@Q Q&% Q1@J)(SETQ  QL%(SSGET )Q&%(SSADD ))(IF  QL%(WHILE (SETQ  Q0#J(SSNAME  QL% 0))(IF (= (CDR (ASSOC  0(SETQ  Q#&(ENTGET  Q0#J))))"POLYLINE")(IF (= (CDR (ASSOC  70 Q#&))0)(PROGN (SETQ  Q0@(CDR (ASSOC  10(ENTGET (SETQ  Q#1J(ENTNEXT  Q0#J))))))(WHILE (/= (CDR (ASSOC  0(ENTGET (ENTNEXT  Q#1J))))"SEQEND")(SETQ  Q#1J(ENTNEXT  Q#1J)))(SETQ  QO1(CDR (ASSOC  10(ENTGET  Q#1J))))(IF (NOT (EQUAL  Q0@ QO1 0.0001))(SSADD  Q0#J Q&%)))))(SSDEL  Q0#J QL%)))(SETQ  Q@Q 0)(SETQ  Q1@J(SSLENGTH  Q&%))(COMMAND "SELECT"Q&%"")(REPEAT  Q1@J(REDRAW (SSNAME  Q&% Q@Q)3)(SETQ  Q@Q(1+  Q@Q)))(PROMPT (STRCAT "\nNumber of unclosed polylines - "(ITOA  Q1@J)))(PRIN1 ))
