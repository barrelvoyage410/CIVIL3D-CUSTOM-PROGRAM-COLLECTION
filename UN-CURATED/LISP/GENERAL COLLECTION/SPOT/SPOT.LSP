(defun new_err (msg)
   (if (/= msg "Function cancelled")
      (if (= msg "quit / exit abort")
         (princ)
         (princ (strcat "\nError: " msg))
      )
      (princ)
   )
   (if old_err (setq *error* old_err))
   (if spotent(redraw spotent 4))
   (princ)
)
   
(defun spotsetx ()
  (setq spotsy (get_tile "spotsy")
        spotla (get_tile "spotla")
        spotsc (atof (get_tile "spotsc"))
        spotro (atof (get_tile "spotro"))
        spotpr (atoi (get_tile "spotpr"))
        spotpar (atoi (get_tile "spotpar"))
        spott_c (atoi (get_tile "spott_c"))
        spotpos (atoi (get_tile "spotpos"))
        spotel0 (atoi (get_tile "spotel0"))
  )
)

(defun c:spotset ()
  (setvar "cmdecho" 0)
  (setq dcl_id (load_dialog "spot.dcl"))
  (new_dialog "spot" dcl_id)
  (if spotsy (set_tile "spotsy" spotsy))
  (if spotla (set_tile "spotla" spotla)(set_tile "spotla" (getvar "clayer")))
  (if spotsc (set_tile "spotsc" (rtos spotsc 2 2)))
  (if spotro (set_tile "spotro" (rtos spotro 2 2)))
  (if spotpr (set_tile "spotpr" (itoa spotpr)))
  (if spotpar (set_tile "spotpar" (itoa spotpar)))
  (if spott_c (set_tile "spott_c" (itoa spott_c)))
  (if spotpos (set_tile "spotpos" (itoa spotpos)))
  (if spotel0 (set_tile "spotel0" (itoa spotel0)))
  (setq x (dimx_tile "LOGO_slide")
        y (dimy_tile "LOGO_slide"))
  (start_image "LOGO_slide")
  (slide_image 0 0 x y "LOGO")
  (end_image)
  (action_tile "spotpar" "(set_tile \"spott_c\" (itoa 0))")
  (action_tile "spott_c" "(set_tile \"spotpar\" (itoa 0))")
  (action_tile "cancel" "(done_dialog 0)")
  (action_tile "accept" "(spotsetx)(done_dialog 1)")
  (start_dialog)
  (unload_dialog dcl_id)
  (princ)
)

(defun c:spot ( / opt pt el helptext1 helptext2 spotval)
  (setq olderr *error* *error* new_err opt "New")
  (if (not spotsy)(setq spotsy "spotx"))
  (if (not spotel)(setq spotel 0.0))
  (while opt
    (if (not (and spotsc spotsy spotro spotpr spotel0 spotpos))(c:spotset))
    (if spotold (redraw spotold 4))
    (initget "Settings Modify Update New")
    (if (setq opt (getpoint "\nSettings/Modify/Update/<New spot grade>: "))
      (cond
        ((= opt "Settings")(c:spotset))
        ((= opt "Modify")(setq opt nil)(spotmod)(if (= optnew "New")(setq opt "New" optnew nil)))
        ((= opt "Update")
            (if (= 0 spotel0)
              (progn
                (setq ans "Help")
                (while (= ans "Help")
                  (initget "Text Z Help") 
                  (setq ans (getkword "\nText/Z coord/Help: "))
                  (cond
                    ((= ans "Text")(graphscr)(setq opt nil)(spotupd "T"))
                    ((= ans "Z")(graphscr)(setq opt nil)(spotupd "Z"))
                    ((= ans "Help")(textscr)
                      (setq helptext1 "\n\nSelecting 'Text' will change the elevation text \n    of all spot grades to match their Z coordinate.")
                      (setq helptext2 "\n\nSelecting 'Z coord' will change the Z coordinate \n    of all spot grades to match their elevation text.")
                      (princ "\n\n\n\n\n\n")(princ helptext1)(princ helptext2)(princ "\n\n\n\n\n")
                    )
                  )
                )
              )
              (princ "\nCurrent settings will not allow this option.")
            )
        )
        (t(progn
            (if (= opt "New")
              (setq pt (getpoint "\nPick new spot location: "))
              (setq pt opt)
            )
            (if (/= 0 (caddr pt))(setq spotel (caddr pt)))
            (if (setq el (getreal (strcat "\nEnter spot elevation <"
                  (rtos spotel 2 spotpr) ">: ")))
              (setq spotel el)
            )
            (if (/= (getvar "clayer") spotla)(command ".layer" "m" spotla ""))
            
            (if (= 1 spotel0)(setq spotz 0)(setq spotz spotel))
            (setq spotval (rtos spotel 2 spotpr))
            (if (= 1 spott_c)(setq spotval (strcat spotval " T/C")))
            (if (= 1 spotpar)(setq spotval (strcat "(" spotval ")")))
            (command ".insert" spotsy ".xy" pt spotel spotsc spotsc 0 spotval)
            (command ".attedit" "" "" "" "" "l" "a" spotro "p" (polar pt (angtof (rtos (+ spotro 90.0)) 0) (* spotsc 0.15)) "")
            (if (= 1 spotpos)
              (if (setq pt (getpoint "\nPick text location: "))
                (command ".attedit" "" "" "" "" "l" "p" pt "")
              )
            )
          )
        )
      )
    )
  )
  (setq opt nil *error* olderr olderr nil)
  (princ)
)

(defun spotmod ( / opt pt el optprmpt spotblk spotatt spotz spotpt spotval)
  (setq opt "Select")
  (while opt
    (if spotatt
      (progn
        (redraw spotatt 3)
        (setq optprmpt "\nAngle/Elevation/Position/eXit/<Select>: ")
        (initget "Angle Elevation Position eXit Select")
      )
      (progn
        (setq optprmpt "\n<Select spot grade>: ")
        (initget "Select")
      )
    )
    (if (setq opt (entsel optprmpt))
      (cond
        ((= opt "Angle")
          (setq spotpt (cdr (assoc 11 (entget spotatt))))
          (if (setq pt (getpoint spotpt "\nPick new text angle: "))
            (progn
              (redraw spotatt 4)
              (command ".attedit" "" "" "" "" spotatt "a" pt "")
            )
          )
        )
        ((= opt "Elevation")
          (setq spotz (cadddr (assoc 10 (entget spotblk))))
          (setq spottxt (cdr (assoc 1 (entget spotatt))))
          (if (= "(" (substr spottxt 1 1))
            (setq spottxt (substr spottxt 2 (- (strlen spottxt) 2)) spotparx 1)
            (setq spotparx 0)
          )
          (setq spotsfx (vl-string-left-trim "0123456789." spottxt))
          (if (setq el (getreal (strcat "\nEnter new elevation <"
                (rtos spotz 2 spotpr) ">: ")))
            (progn
              (redraw spotatt 4)
              (setq spotel el)
              (setq spotval (rtos spotel 2 spotpr))
              (if spotsfx (setq spotval (strcat spotval spotsfx)))
              (if (= 1 spotparx)(setq spotval (strcat "(" spotval ")")))
              (command ".attedit" "" "" "" "" spotatt "V" "R" spotval "")
              (if (= 1 spotel0)(setq spotel 0))
              (command ".move" spotblk "" (list 0 0 spotz)(list 0 0 spotel))
            )
          )
        )
        ((= opt "Position")
          (setq spotpt (cdr (assoc 11 (entget spotatt))))
          (if (setq pt (getpoint spotpt "\nPick new text location: "))
            (progn
              (redraw spotatt 4)
              (command ".attedit" "" "" "" "" spotatt "p" pt "")
            )
          )
        )
        ((= opt "eXit")(setq optnew "New" opt nil))
        (t
          (progn
            (if spotatt (redraw spotatt 4))
            (setq spotatt (car opt))
            (if (= "INSERT" (cdr (assoc 0 (entget spotatt))))
              (progn
                (setq spotblk (car opt))
                (setq spotatt (entnext spotblk))
                (if spotold (redraw spotold 4))
                (setq spotold spotatt)
                (redraw spotatt 3)
              )
              (setq spotatt nil)
            )
          )
        )
      )
      (if spotatt (redraw spotatt 4))
    )
  )
)

(defun spotupd ( spotopt / spotopt spotblk spotatt spotz spottxt spotelx spotsfx spotparx spotval a b)
  (princ "\nChecking all spot blocks...")
  (if (setq spotss (ssget "X" (list  (cons 0 "INSERT")(cons 2 spotsy))))
    (progn
      (if (= "Z" spotopt)
        (setq a "Z coordinate" b "text")
        (setq b "Z coordinate" a "text")
      )
      (setq n 0 t (sslength spotss) c 0)
      (while (< n t)
        (setq spotblk (ssname spotss n))
        (setq spotatt (entnext spotblk))
        (setq spotz (cadddr (assoc 10 (entget spotblk))))
        (setq spottxt (cdr (assoc 1 (entget spotatt))))
        (if (= "(" (substr spottxt 1 1))
          (setq spottxt (substr spottxt 2 (- (strlen spottxt) 2)) spotparx 1)
          (setq spotparx 0)
        )
        (setq spotsfx (vl-string-left-trim "0123456789." spottxt))
        (setq spotelx (atof (substr spottxt 1 (- (strlen spottxt)(strlen spotsfx)))))
        (if (/= spotz spotelx)
          (if (= "Z" spotopt)
            (progn
              (command ".move" spotblk "" (list 0 0 spotz)(list 0 0 spotelx))
              (setq c (1+ c))
            )
            (progn
              (setq spotval (rtos spotz 2 spotpr))
              (if spotsfx (setq spotval (strcat spotval spotsfx)))
              (if (= 1 spotparx)(setq spotval (strcat "(" spotval ")")))
              (command ".attedit" "" "" "" "" spotatt "V" "R" spotval "")
              (setq c (1+ c))
            )
          )
        )
	(setq n (1+ n))
      )
      (princ (strcat "\nChecked " (itoa n) " spot grades, updated " a " of " (itoa c) " spot(s) to match " b "."))
    )
  )
)
