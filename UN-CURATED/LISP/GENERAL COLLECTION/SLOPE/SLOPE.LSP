(defun c:slope ()
  (setq dcl_id (load_dialog "slope.dcl"))
  (new_dialog "slope" dcl_id)
  (if offset (set_tile "off_set" (rtos offset)))
  (if chelev (set_tile "ch_elev" (rtos chelev)))
  (setq x (dimx_tile "LOGO_slide")
        y (dimy_tile "LOGO_slide"))
  (start_image "LOGO_slide")
  (slide_image 0 0 x y "LOGO")
  (end_image)
  (action_tile "cancel" "(done_dialog 0)")
  (action_tile "accept" (strcat "(progn "
    "(setq offset (atof (get_tile \"off_set\")))"
    "(setq chelev (atof (get_tile \"ch_elev\")))"
    "(done_dialog 1))")
  )
  (setq doslope (start_dialog))
  (unload_dialog dcl_id)
  (if (= doslope 1)
    (progn
      (if (and offset chelev)
        (while (setq ent (entsel "\nSelect object to project."))
          (if (= "LWPOLYLINE" (cdr (assoc 0 (entget (car ent)))))
            (setq entelev (cdr (assoc 38 (entget (car ent)))))
            (setq entelev (caddr (cdr (assoc 10 (entget (car ent))))))
          )
          (princ (strcat "\nEntity elevation: " (rtos entelev)))
          (while (setq pnt (getpoint "\nIndicate direction to offset."))
            (command ".offset" offset ent pnt "")
            (command ".move" "l" "" (list 0 0 0) (list 0 0 chelev))
            (setq ent (list (entlast)(cdr (assoc 10 (entget (entlast))))))
            (if (= "LWPOLYLINE" (cdr (assoc 0 (entget (car ent)))))
              (setq entelev (cdr (assoc 38 (entget (car ent)))))
              (setq entelev (caddr (cdr (assoc 10 (entget (entlast))))))
            )
            (princ (strcat "\nNew entity elevation: " (rtos entelev)))
          )
        )
      )
    )
  )
  (princ)
)
