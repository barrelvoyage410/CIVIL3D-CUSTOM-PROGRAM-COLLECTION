(defun park_get_file ()
  (if (not isleang)
    (if (findfile (strcat (getvar "dwgprefix") "park.set"))
      (progn
        (setq file_id  (open (strcat (getvar "dwgprefix") "park.set") "r")
              isleang  (atof (read-line file_id))
              islemin  (atof (read-line file_id))
              islera   (atof (read-line file_id))
              islerr   (atof (read-line file_id))
              islelen  (atof (read-line file_id))
              stallwid (atof (read-line file_id))
        )
        (close file_id)
      )
    )
  )
)

(defun park_set_file ()
  (setq file_id  (open (strcat (getvar "dwgprefix") "park.set") "w"))
  (write-line (rtos isleang)  file_id)
  (write-line (rtos islemin)  file_id)
  (write-line (rtos islera)   file_id)
  (write-line (rtos islerr)   file_id)
  (write-line (rtos islelen)  file_id)
  (write-line (rtos stallwid) file_id)
  (close file_id)
)



(defun park_get_tile ()
  (if (= "1" (get_tile "baseang"))
    (setq isleang (atof (get_tile "isleang")))
    (setq isleang (atof (get_tile "islecang")))
  )
  (setq islelen (atof (get_tile "islelen"))
        islera (atof (get_tile "islera"))
        islerr (atof (get_tile "islerr"))
        islemin (atof (get_tile "islemin"))
        stallwid (atof (get_tile "stallwid"))
        stalloff (atof (get_tile "stalloff"))
  )
)

(defun park_updt_tile (tile)
  (cond
    ((= "isleang" tile)(set_tile "isleang"
      (rtos (- 180 (atof (get_tile "islecang"))))))
    ((= "islecang" tile)(set_tile "islecang"
      (rtos (- 180 (atof (get_tile "isleang"))))))
    ((= "islelen" tile)(set_tile "islelen"
      (rtos (* (atof (get_tile "stalllen"))(abs (sin (* (/ pi 180) isleang)))))))
    ((= "stalllen" tile)(set_tile "stalllen"
      (rtos (/ (atof (get_tile "islelen"))(abs (sin (* (/ pi 180) isleang)))))))
    ((= "stallwid" tile)(set_tile "stallwid"
      (rtos (* (atof (get_tile "stalloff"))(abs (sin (* (/ pi 180) isleang)))))))
    ((= "stalloff" tile)(set_tile "stalloff"
      (rtos (/ (atof (get_tile "stallwid"))(abs (sin (* (/ pi 180) isleang)))))))
  )
)

(defun park_set_tile ()
  (if (not isleang)(setq isleang 90.0))
  (while (>= isleang 180)
    (setq isleang (- isleang 180))
  )
  (if (= 0 isleang)(setq isleang 90.0))
  (if (<= isleang 90.0)
    (progn (set_tile "isleang" (rtos isleang))
           (set_tile "islecang" (rtos (- 180 isleang)))
           (set_tile "baseang" "1")
    )
    (progn (set_tile "islecang" (rtos isleang))
           (set_tile "isleang" (rtos (- 180 isleang)))
           (set_tile "compang" "1")
    )
  )
  (park_mode_tile)
  (if islera (set_tile "islera" (rtos islera)))
  (if islerr (set_tile "islerr" (rtos islerr)))
  (if islemin (set_tile "islemin" (rtos islemin)))
  (if islelen (set_tile "islelen" (rtos islelen)))
  (park_updt_tile "stalllen")
  (if stallwid (set_tile "stallwid" (rtos stallwid)))
  (park_updt_tile "stalloff")
)

(defun park_mode_tile ()
  (if (= isleang 90)
    (progn
      (mode_tile "islecang" 1)
      (mode_tile "islelen" 1)
      (mode_tile "stalloff" 1)
    )
    (progn
      (mode_tile "islecang" 0)
      (mode_tile "islelen" 0)
      (mode_tile "stalloff" 0)
    )
  )
)

(defun c:park ()
  (setvar "cmdecho" 0)
  (setq old_err *error* *error* c:nse_err)
  (setq dcl_id (load_dialog "park.dcl"))
  (new_dialog "park" dcl_id)
  (park_get_file)
  (park_set_tile)
  (setq x (dimx_tile "LOGO_slide")
        y (dimy_tile "LOGO_slide"))
  (start_image "LOGO_slide")
  (slide_image 0 0 x y "LOGO")
  (end_image)
  (action_tile "isleang" "(park_updt_tile \"islecang\")
                          (park_get_tile)(park_set_tile)")
  (action_tile "islecang" "(park_updt_tile \"isleang\")
                          (park_get_tile)(park_set_tile)")
  (action_tile "islelen" "(park_updt_tile \"stalllen\")
                          (park_get_tile)(park_set_tile)")
  (action_tile "stalllen" "(park_updt_tile \"islelen\")
                          (park_get_tile)(park_set_tile)")
  (action_tile "stallwid" "(park_updt_tile \"stalloff\")
                          (park_get_tile)(park_set_tile)")
  (action_tile "stalloff" "(park_updt_tile \"stallwid\")
                          (park_get_tile)(park_set_tile)")
  (action_tile "cancel" "(done_dialog 0)")
  (action_tile "accept" "(park_get_tile)(park_set_file)(done_dialog 1)")
  (setq park (start_dialog))
  (unload_dialog dcl_id)
  (princ)
)
