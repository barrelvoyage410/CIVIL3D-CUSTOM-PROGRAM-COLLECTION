;;;                NEZ.LSP created 09:16:27 Friday, 08-11-1995
;;;                    by Mark Evinger, CIS ID 73162,1676
;;;                 Copyright © 1995-1998, Cad Elf Inc. *<:)-|-<
;;; This routine will search the drawing for the selected block  and  write
;;; the xyz coordinates of all instances of the block to an ascii text file
;;; in a  comma-delimited  PNEZ  format. (point,northing,easting,elevation)
;;; The point  numbers  are  "randomly" generated by using a counter of how
;;; many blocks are in the dwg.  The point numbers usually increment in the
;;; order in which the blocks were created,  meaning  that  the  lower  the
;;; number, the earlier in the dwg database the block was inserted.
;;;    The ascii file will be generated using the WORLD coordinate system!

;;; revised 17:34:20 Friday, 01-17-1997 to also write out PNEZ stuff for
;;; AutoCad "POINT" entities -  also known as nodes. Watch the prompts as
;;; the program runs, it tells you what kind of entity you are writing out
;;; Node or Block.

;;; revised 08/13/98 10:33:21 AM to account for changing OSMODE var,  Added
;;; (moder) to return to known state at end of program.

;;; revised 03-20-2007 to check for serial number

;---------------------------------------------------------------------------;
; save specified mode settings                                              ;
;---------------------------------------------------------------------------;
(defun MODESAVE (a_A)
  (setq MLST '())
  (repeat (length a_A)
    (setq MLST (append MLST (list (list (car a_A) (getvar (car a_A))))))
  (setq a_A (cdr a_A)))
)
;---------------------------------------------------------------------------;
; restore saved mode settings                                               ;
;---------------------------------------------------------------------------;
(defun MODER ()
  (repeat (length MLST)
    (setvar (caar MLST) (cadar MLST))
    (setq MLST (cdr MLST))
  )
)
;---------------------------------------------------------------------------;
;error handler                                                              ;
;---------------------------------------------------------------------------;
(defun nez_err (s)                ;If an error (such as CTRL-C) occurs
  (if (/= s "Function cancelled") ;while this command is active...
    (princ (strcat "\nError: " s))
  )
  (setq *error* old_err)          ;Restore old *error* handler
  (moder)                         ;return modes to old values
  (princ)
)
;---------------------------------------------------------------------------;
;entity filter function
;---------------------------------------------------------------------------;
(defun ent_get1 ()
  (prompt "\nSelect BLOCK to write PNEZ Coordinates :")
  (setq FP (car (entsel)))
  (while (= FP nil)
    (prompt "\nNothing Selected!")
    (prompt "\nSelect BLOCK to write PNEZ Coordinates :")
    (setq FP (car (entsel)))
  ); end while FP=nil
  (setq IS_BLOCK (cdr (assoc 0 (entget FP))))
  (cond
    ((= IS_BLOCK "INSERT")
      (setq BLOCK_NAME (cdr (assoc 2 (entget FP))))
      (setq BLKLIST (tblsearch "block" BLOCK_NAME))
      (setq BLKTYPE (cdr (assoc 70 BLKLIST)))
      (if (= (logand BLKTYPE 4) 4)        ; is selected block really xref?
        (progn                                     ; yes
          (setq XREFPATH (cdr (assoc 1 BLKLIST)))  ; it is
          (prompt (strcat "\nSelected entity is an Xref, path "XREFPATH".dwg"))
          (setq XREF_TF nil)
        );end progn
        (setq XREF_TF t)
      );end if
    );end block and xref
    ((/= IS_BLOCK "INSERT")
      (if (= IS_BLOCK "POINT")
        (setq XREF_TF t)
        (progn
          (prompt (strcat "\nSelected entity is "IS_BLOCK" !! "))
          (setq XREF_TF nil)
        );end progn (else)
      );end if
    ); end all other picks
  );end cond
);end defun ent_get1
;---------------------------------------------------------------------------;
(defun c:nez () ;( /_X_Y_Z BLKLIST BLKTYPE BLOCK_NAME f FP INSERT_NUM
  ;IS_BLOCK l n P1x P1y P1z ss TEXT_OUT xref_TF XREFPATH )
  (if (cgl_check_serial)
    (progn
  ;-=-=-=-=-=-=-=-=-=-=-=-=-=-=-=-=-=-=-=-=-=-=-=-=-=-=-=-=-=-=-=-=-=-=-=-=-=-;
  (setq old_err *error*         ; use special error handling function
  *error* NEZ_err)
  ;-=-=-=-=-=-=-=-=-=-=-=-=-=-=-=-=-=-=-=-=-=-=-=-=-=-=-=-=-=-=-=-=-=-=-=-=-=-;
  (modesave '("BLIPMODE" "CMDECHO" "COORDS" "DIMZIN" "GRIPS" "OSMODE" "AUNITS"));save modes
  (setvar "BLIPMODE" 0)    ;turn off blips
  (setvar "CMDECHO" 0)     ;turn off command echo
  (setvar "COORDS" 2)      ;sets coords to show distance & angle
  (setvar "DIMZIN" 0)      ;turn off dimzin (controls leading/trailing 0's)
  (setvar "GRIPS" 0)       ;turn off grips
  (setvar "OSMODE"  0)     ;turn off osnaps
  (setvar "AUNITS" 0)      ;set angular units to degrees only
  ;---------------------------------------------------------------------------;
  (setq ss nil)
  (setq xref_TF nil)

  (while (= xref_tf nil)
    (ent_get1)
  )

  (cond ((= XREF_TF t)
      (if (= IS_BLOCK "POINT")
        (setq ss (ssget "X" (list (cons 0 IS_BLOCK)))   ENT_TYPE "Node" BLOCK_NAME IS_BLOCK)
        (setq ss (ssget "X" (list (cons 2 BLOCK_NAME))) ENT_TYPE "Block")
      );end if
      (prompt (strcat "\nEnter name of output file to write PNEZ information for "ENT_TYPE" "BLOCK_NAME" : "))
      (setq FILE_OUT (getfiled "Enter PNEZ Out File Name" (getvar "dwgname") "NEZ" 1))
      (if FILE_OUT
        (progn
          (setq f (open FILE_OUT "w"))
          (setq n (sslength ss))
          (setq l 0)
          (while (< l n)
            (setq INSERT_NUM (+ l 1.0))
            (setq _X_Y_Z (cdr (assoc 10 (setq elist (entget (ssname ss l))))))
            (setq P1x (car _X_Y_Z))
            (setq P1y (cadr _X_Y_Z))
            (setq P1z (caddr _X_Y_Z))
            (setq TEXT_OUT (strcat (rtos INSERT_NUM 2 0) "," (rtos P1y 2 8) "," (rtos P1x 2 8) "," (rtos P1z 2 8)))
            (write-line TEXT_OUT)
            (write-line TEXT_OUT f)
            (setq l (1+ l))
          );end while
          (close f)
          (princ)
          (print)
          (write-line (strcat "\n"ENT_TYPE": "BLOCK_NAME " --> "(rtos INSERT_NUM 2 0)" Entries written in \nPoint,Northing,Easting,Z_elevation format to file "FILE_OUT))
          (princ)
        );end progn
        (progn
          (prompt "\nNo filename given...  Function Cancelled!!")
          (princ)
        );end progn
      );end if
    );end true
  );end cond
  (moder); return modes to original state.
    );end checker progn
    (alert "  Not running on an authorized CGL install.\n\nCopyright Cowhey Gudmundson Leder, Ltd.")
    );end if
    (princ)
); end  defun c:NEZ
