(defun ERRHNDL (ERR1)
  (if (/= ERR1 "Function cancelled")
    (princ (strcat "\nError: " ERR1))
  )
  (setq *ERROR* W)
  (prin1)
)

(defun C:JUST (/ A B C D E F G H J K L M N P Q R S TR U V W)
  (setvar "menuecho" 0)
  (setq W       *ERROR*
        *ERROR* ERRHNDL
  )
  (setq V 0)
  (if (null R1)
    (setq R1 "S")
  )
  (princ (strcat "\njustify to: average of (E)ntire set/ (S)pec'd text line/"
                 "\nor (D)ragged ref. line <"
                 R1
         )
  )
  (initget "E S D")
  (setq A (getkword ">: "))
  (if (= A NIL)
    (setq A R1)
    (setq R1 A)
  )
  (setq R1 (strcase A))
  (setvar "OSMODE" 0)
  (if (setq B (ssget))
    (progn
      (cond
        ((= R1 "S")
         (setq C (entsel "Selct text line for base reference: "))
         (while (or (= C NIL)
                    (/= "TEXT" (cdr (assoc 0 (entget (car C)))))
                )
           (princ "\n")
           (princ "\n")
           (setq C (entsel "\nNo text selected....Try again: "))
         )
         (setq D (cdr (assoc 72 (setq E (setq F (entget (car C)))))))
         (setq F (subst (cons 72 2) (assoc 72 F) F))
         (entmod F)
         (setq F (entget (car C)))
         (setq G (distance (cdr (assoc 10 F)) (cdr (assoc 11 F))))
         (setq F E)
         (entmod F)
        )

        ((= R1 "D")
         (setvar "orthomode" 1)
         (princ "\n")
         (princ "\n")
         (setq G (getdist "\nPick startpoint for text width ref. line:"))
        )

        ((= R1 "E")
         (setq H -1
               J 0
               K 0
         )
         (while (setq L (ssname B (setq H (1+ H))))
           (setq N (entget L))
           (if (eq (cdr (assoc 0 N)) "TEXT")
             (progn
               (setq D (cdr (assoc 72 (setq E (setq F (entget L))))))
               (setq F (subst (cons 72 2) (assoc 72 F) F))
               (entmod F)
               (setq F (entget L))
               (setq J (+ (distance (cdr (assoc 10 F))
                                    (cdr (assoc 11 F))
                          )
                          J
                       )
               )
               (setq F E)
               (entmod F)
               (setq K (1+ K))
             )
           )
         )
         (setq G (/ J K))
        )
      )

      (setq U -1)
      (while (setq M (ssname B (setq U (1+ U))))
        (setq N (entget M))
        (if (eq (cdr (assoc 0 N)) "TEXT")
          (progn
            (setq V (1+ V))
            (setq D (cdr (assoc 72 (setq E (setq F (entget M))))))
            (setq F (subst (cons 72 2) (assoc 72 F) F))
            (entmod F)
            (setq F (entget M))
            (setq P (distance (cdr (assoc 10 F)) (cdr (assoc 11 F))))
            (setq F E)
            (entmod F)
            (setq Q  (/ G P)
                  S  (assoc 41 F)
                  TR (* Q (cdr S))
                  F  (subst (cons 41 TR) S F)
            )
            (entmod F)
          )
        )
      )
      (if (= 0 V)
        (progn
          (princ "\nNo text was selected for justification.")
          (princ)
        )
        (progn
          (princ (strcat "\nText justified on " (itoa V)))
          (princ " line(s).")
          (princ)
        )
      )
    )
    (progn
      (princ "\nNo entities selected - routine terminated.")
      (princ)
    )
  )
  (setq *ERROR* W)
  (princ)
)
