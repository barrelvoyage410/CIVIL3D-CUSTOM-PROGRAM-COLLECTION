(DEFUN C:CHELEV ()
        (SETVAR "CMDECHO" 0 )
        (SETQ INDEX 0
                G1 (SSGET)
                SG1 (SSLENGTH G1)
        )
        (IF (= EL NIL)
          (SETQ EL 0)
        )
        (IF (= NELV NIL)
          (SETQ NELV 0)
        )
        (SETQ A NELV)
        (PRINC "\nENTER DESIRED ELEVATION : DEFAULT <")
        (PRINC NELV)
        (PRINC "> ")
        (SETQ NELV (GETREAL))
        (IF (= NELV NIL)
                (SETQ NELV A)
        )
        (REPEAT SG1
                (SETQ E (SSNAME G1 INDEX))
                (SETQ E1 (ENTGET (SSNAME G1 INDEX)))
                (SETQ E1 (CAR (CDR (CDR (CDR (ASSOC 10 E1))))))
                (SETQ DIFF (- NELV E1))
                (SETQ TXELV (STRCAT "@0,0," (RTOS DIFF 2 4)))
                (COMMAND "._MOVE" E "" "0,0,0" TXELV)
                (SETQ INDEX (+ INDEX 1))
        )
        (SETVAR "CMDECHO" 1)
        (PRINC)
); END CHELEV.LSP
