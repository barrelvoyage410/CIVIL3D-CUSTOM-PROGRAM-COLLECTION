(defun C:E2P (/ adoc el ssnab en item lays lay lock pell ptcen osm count)
  (setq adoc (vla-get-activedocument (vlax-get-acad-object)))
  (setq lays (vla-get-layers adoc) count 0)
  (vla-startundomark adoc)
  (princ "\nSelect Ellipse")
  (setq ssnab (ssget '((0 . "ELLIPSE"))))
  (setq pell (getvar "PELLIPSE"))
  (setq osm (getvar "OSMODE"))
  (setvar "OSMODE" 0)
  (setvar "PELLIPSE" 1)
  (while (and ssnab (> (sslength ssnab) 0))
    (setq el (ssname ssnab 0))
    (setq en (vlax-ename->vla-object el))
    (setq lay (vla-item lays (vla-get-layer en)))
    (if (= (vla-get-lock lay) :vlax-true)
      (progn (vla-put-lock lay :vlax-false)
      (setq lock (cons lay lock))))
    (setq item (vla-get-ObjectName en))
    (cond
      ((= item "AcDbEllipse")(setq count (1+ count))
       (setq ptcen (vlax-safearray->list(vlax-variant-value (vla-get-center en))))
       (command "_.ellipse"  "_C" (trans ptcen 0 1)
                (trans (mapcar '+ ptcen (vlax-safearray->list(vlax-variant-value (vla-get-MajorAxis en)))) 0 1)
                (trans (mapcar '+ ptcen (vlax-safearray->list(vlax-variant-value (vla-get-MinorAxis en)))) 0 1))
       (mapcar '(lambda (x y)(vlax-put-property (vlax-ename->vla-object (entlast)) x y))
               '(Linetype LineWeight Color Layer)
               (mapcar '(lambda (x)(vlax-get-property en x))
                       '(Linetype LineWeight Color Layer))
               )
       (vla-Delete en)
      )
      (t nil)
    )
    (ssdel el ssnab)
  )
  (setvar "PELLIPSE" pell)
  (setvar "OSMODE" osm)
  (if lock (foreach x lock (vla-put-lock x :vlax-true)))
  (vla-endundomark adoc)
  (princ (strcat "\nTransformation " (itoa count) " Ellipse is completed"))
  (princ)
)
(princ "\nType E2P to run command")
