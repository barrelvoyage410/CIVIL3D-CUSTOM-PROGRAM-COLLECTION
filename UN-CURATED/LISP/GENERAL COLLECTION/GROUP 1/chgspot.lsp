; CHGSPOT.LSP By Rod Roberts of R.A.S. 12/5/95
; Changes spot elevation annotations (text) by a constant value.

(defun newerr (msg)
   (if (/= msg "Function cancelled")
      (if (= msg "quit / exit abort")
	 (princ)
	 (princ (strcat "\nError: " msg))
      )
      (princ)
   )
   (if olderr (setq *error* olderr))
   (princ)
)

;   main program
(defun C:CHGSPOT ( / ss n val i b p new opt entdat)
  (setvar "cmdecho" 0)
  (setq olderr *error*)
  (setq *error* newerr)
  (setq p (getvar "LUPREC"))
  (setq chg (getreal "Change in elevation: "))
  (princ "\nSelect SPOT ELEVATIONS to change.")
  (if (setq ss (ssget '((0 . "TEXT"))))
    (progn
      (setq n 0 i 0 b 0)
      (while (< n (sslength ss))
        (setq entdat (entget (ssname ss n)))
        (setq val (read (cdr (assoc 1 entdat))))
        (if (and val (or (= 'INT (type val))(= 'REAL (type val))))
          (progn
            (setq new (+ chg val))
            (setq entdat (subst (cons 1 (rtos new 2 p))(assoc 1 entdat) entdat))
            (entmod entdat)
            (setq i (1+ i) val nil new nil)
          )
          (setq b (1+ b))
	)
	(setq n (1+ n))
      )
      (princ (strcat "\nChanged " (itoa i) " spot elevations."))
      (if (< 0 b)(princ (strcat "\nUnable to change " (itoa b) " text entities.")))
    )
  )
  (setvar "cmdecho" 1)
  (setq ss nil n nil i nil b nil p nil entdat nil)
  (setq *error* olderr)
  (princ)
)
