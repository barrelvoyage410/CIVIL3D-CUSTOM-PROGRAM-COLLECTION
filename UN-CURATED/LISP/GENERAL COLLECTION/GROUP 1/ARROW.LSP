(defun c:ARROW ( / SP ANGP ARRANG LENG EP)
  (setq SP (getpoint "\n Starting point for arrow"))
  (setq ANGP (getpoint SP "\n Select arrow angle"))
  (setq ARRANG (angle sp angp))
  (if (= 0.0 (getvar "DIMASZ"))
      (setq LENG 1.0)(setq LENG (getvar "DIMASZ")))
      (setq EP (polar sp arrang (* LENG (getvar "DIMSCALE"))))
  (command "PLINE" sp "W" "0.0" (* 0.333 LENG (getvar"DIMSCALE"))
            EP "W" "0.0" "0.0" "ARC"))
