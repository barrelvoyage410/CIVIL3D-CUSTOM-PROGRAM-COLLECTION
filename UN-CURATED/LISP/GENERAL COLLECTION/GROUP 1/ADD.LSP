; ADD.LSP By Rod Roberts of R.A.S. 2/1/95
; Totals parking spaces labeled w/parklbl.lsp.
; (Can be used to total any numbers inserted as text)

(defun newerr (msg)
   (if (/= msg "Function cancelled")
      (if (= msg "quit / exit abort")
	 (princ)
	 (princ (strcat "\nError: " msg))
      )
      (princ)
   )
   (if olderr (setq *error* olderr))
   (princ)
)

;   main program
(defun C:ADD ( / ss n num tot bad pnt str j x p opt)
  (setvar "cmdecho" 0)
  (setq olderr *error*)
  (setq *error* newerr)
  (princ "\nSelect TEXT items to total.")
  (if (setq ss (ssget '((0 . "TEXT"))))
    (progn
      (setq n 0 tot 0.0 bad 0)
      (while (< n (sslength ss))
	(setq num (read (cdr (assoc 1 (entget (ssname ss n))))))
	(if (and num (or (= 'INT (type num))(= 'REAL (type num))))
	  (setq tot (+ tot num))
	  (setq bad (1+ bad))
	)
	(setq n (1+ n))
      )
    )
  )
  (setq p (getvar "LUPREC"))
  (princ (strcat "\nAdded " (itoa (- (sslength ss) bad)) " text items."))
  (if (< 0 bad)
    (princ (strcat "\nUnable to add " (itoa bad) " text item(s) to total."))
  )
  (princ (strcat "\nTotal = " (rtos tot 2 p) "."))
  (setq str "\nUpdate/Insert/<Quit>: ")
  (initget 128 "Update Insert")
  (setq opt (getpoint str))
  (if (= opt "Update")
    (progn
      (setq x (getint (strcat "Precision <" (itoa p) ">: ")))
      (if x (setq p x))
      (if (setq entdat (entget (car (entsel "Select text to update."))))
        (if (= "TEXT" (cdr (assoc 0 entdat)))
          (progn
            (setq entdat (subst (cons 1 (rtos tot 2 p))(assoc 1 entdat) entdat))
            (entmod entdat)
          )
        )
      )
    )
  )
  (if (= opt "Insert")
    (progn
      (setq str "\nPrecision/Justification/Style/Text insertion point: ")
      (setq j "BL")
      (setq pnt "0")
      (while pnt
        (initget "Precision Justification Style")
        (setq pnt (getpoint str))
        (cond
          ((= pnt "Precision")(setq p (getint "Number of places for decimal: ")))
          ((= pnt "Justification")
            (progn
              (initget "Left Middle Right")
              (setq j (getkword "Justification <Left/Middle/Right> "))
              (cond
                ((= j "Left")(setq j "BL"))
                ((= j "Middle")(setq j "MC"))
                ((= j "Right")(setq j "BR"))
              )
            )
          )
          ((= pnt "Style")
            (progn
              (setvar "cmdecho" 1)
              (princ "\n")
              (command "'Style" pause pause pause pause pause pause pause pause)
              (setvar "cmdecho" 0)
            )
          )
          (pnt
            (progn
              (if (= 0 (cdr (assoc 40 (tblsearch "STYLE" (getvar "textstyle")))))
                (command "TEXT" "J" j pnt (getvar "textsize") "" (rtos tot 2 p))
                (command "TEXT" "J" j pnt "" (rtos tot 2 p))
              )
              (setq pnt nil)
            )
          )
        )
      )
    )
  )
  (setvar "cmdecho" 1)
  (setq ss nil n nil num nil tot nil bad nil pnt nil str nil p nil j nil)
  (setq *error* olderr)
  (princ)
)
