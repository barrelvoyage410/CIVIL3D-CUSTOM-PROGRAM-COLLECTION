(setq acadver (vl-registry-read "HKEY_LOCAL_MACHINE\\SOFTWARE\\Autodesk\\AutoCAD" "Curver"))
(setq acadnum (vl-registry-read (strcat "HKEY_LOCAL_MACHINE\\SOFTWARE\\Autodesk\\AutoCAD\\" acadver) "Curver"))
(if (and (= acadver "R15.0")(or(= acadnum "ACAD-1:409")(= acadnum "ACAD-8:409")(= acadnum "ACAD-138:409")))
  (progn
    (setq dwgsize (strcase(substr(getvar "dwgname") 6 1)))
    (setq profilename (vl-registry-read (strcat "HKEY_CURRENT_USER\\Software\\Autodesk\\AutoCAD\\" acadver "\\" acadnum "\\Profiles")))
    (setq plotstampkey (strcat "HKEY_CURRENT_USER\\Software\\Autodesk\\AutoCAD\\" acadver "\\" acadnum "\\Profiles\\" profilename "\\Dialogs\\Plot Stamp"))
    (vl-registry-write plotstampkey "Comment" "")
    (vl-registry-write plotstampkey "DateAndTime" 1)
    (vl-registry-write plotstampkey "DrawingName" 1)
    (vl-registry-write plotstampkey "Layoutname" 1)
    (vl-registry-write plotstampkey "Location" 0)
    (vl-registry-write plotstampkey "LogFile" 1)
    (vl-registry-write plotstampkey "LogFilePath" "L:\\Acad\\Plotlog\\Plot.log")
    (vl-registry-write plotstampkey "LoginName" 1)
    (vl-registry-write plotstampkey "OffsetRelLoc" 0)
    (vl-registry-write plotstampkey "Orientation" 0)
    (vl-registry-write plotstampkey "PaperSize" 0)
    (vl-registry-write plotstampkey "PlotDeviceName" 0)
    (vl-registry-write plotstampkey "PlotScale" 0)
    (vl-registry-write plotstampkey "PlotStamp" 1)
    (vl-registry-write plotstampkey "StampOnOneLine" 1)
    (vl-registry-write plotstampkey "TextFontCharSet" 2)
    (vl-registry-write plotstampkey "TextFont" "RomanD")
    (vl-registry-write plotstampkey "TextFontPitch" 0)
    (if (or (= dwgsize "A")(= dwgsize "B")(= dwgsize "L"))
      (progn
        (vl-registry-write plotstampkey "TextHeight" "0.060000")
        (vl-registry-write plotstampkey "PSPFilename" "L:\\Acad\\PlotStamp\\STD06.pss")
      )
      (progn
        (vl-registry-write plotstampkey "TextHeight" "0.080000")
        (vl-registry-write plotstampkey "PSPFilename" "L:\\Acad\\PlotStamp\\STD08.pss")
      )
    )
    (vl-registry-write plotstampkey "Upsidedown" 0)
    (vl-registry-write plotstampkey "XOffset" "0.000000")
    (vl-registry-write plotstampkey "YOffset" "0.000000")
    (vl-registry-write plotstampkey "Units" 0)
  )
)
(princ)

(defun c:plotstampoff ()
  (setq acadver (vl-registry-read "HKEY_LOCAL_MACHINE\\SOFTWARE\\Autodesk\\AutoCAD" "Curver"))
  (setq acadnum (vl-registry-read (strcat "HKEY_LOCAL_MACHINE\\SOFTWARE\\Autodesk\\AutoCAD\\" acadver) "Curver"))
  (if (and (= acadver "R15.0")(or(= acadnum "ACAD-1:409")(= acadnum "ACAD-8:409")(= acadnum "ACAD-138:409")))
    (progn
      (setq profilename (vl-registry-read (strcat "HKEY_CURRENT_USER\\Software\\Autodesk\\AutoCAD\\" acadver "\\" acadnum "\\Profiles")))
      (setq plotstampkey (strcat "HKEY_CURRENT_USER\\Software\\Autodesk\\AutoCAD\\" acadver "\\" acadnum "\\Profiles\\" profilename "\\Dialogs\\Plot Stamp"))
      (vl-registry-write plotstampkey "PlotStamp" 0)
    )
  )
  (princ "\nPlotstamp is OFF.")
  (princ)
)
(defun c:plotstampon ()
  (setq acadver (vl-registry-read "HKEY_LOCAL_MACHINE\\SOFTWARE\\Autodesk\\AutoCAD" "Curver"))
  (setq acadnum (vl-registry-read (strcat "HKEY_LOCAL_MACHINE\\SOFTWARE\\Autodesk\\AutoCAD\\" acadver) "Curver"))
  (if (and (= acadver "R15.0")(or(= acadnum "ACAD-1:409")(= acadnum "ACAD-8:409")(= acadnum "ACAD-138:409")))
    (progn
      (setq profilename (vl-registry-read (strcat "HKEY_CURRENT_USER\\Software\\Autodesk\\AutoCAD\\" acadver "\\" acadnum "\\Profiles")))
      (setq plotstampkey (strcat "HKEY_CURRENT_USER\\Software\\Autodesk\\AutoCAD\\" acadver "\\" acadnum "\\Profiles\\" profilename "\\Dialogs\\Plot Stamp"))
      (vl-registry-write plotstampkey "PlotStamp" 1)
    )
  )
  (princ "\nPlotstamp is ON.")
  (princ)
)
