;VERSION 9.0 (2/09/1988) Copyright 1987, 1988 DCA Engineering, Inc.
;PROGRAM PARKSTP  DRAWS A KNOWN NUMBER OF STALLS
;MODIFIED BY RPR OF NATIONAL SURVEY & ENGINEERING 4/10/91

(defun C:PARKSTP ()
  (setvar "cmdecho" 0)
  (if (null c:park)(load "park"))
  (if (or (null stalloff)(null islelen))
     (c:park)
     (progn
        (setq sa (getvar "snapang"))
        (setq os (getvar "osmode"))
        (while (setq pt1(getpoint "\nStarting point: "))
           (initget 1)
           (setq pt2(getpoint pt1 "\nEnding point: "))
           (setq sta (fix (/ (distof(rtos(distance pt1 pt2))) stalloff)))
           (setq wid (/ (abs (distance pt1 pt2)) sta))
           (if (> (+ sta 1) 1)
              (progn
                 (setq ss (ssadd))
                 (setq ang1(angle pt1 pt2))
                 (setq ang2(+ (angle pt2 pt1)(angtof (rtos isleang))))
                 (setvar "osmode" 0)
                 (setq pt3(polar pt1 ang2 (/ islelen (sin (angtof (rtos isleang))))))
                 (command "line" pt1 pt3 space)
                 (ssadd (entlast) ss)
                 (setvar "snapang" ang1)
                 (command "array" "l" "" "r" "1" (+ 1 sta) wid)
                 (ssadd (entlast) ss)
                 (command "erase" ss "")
              )
              (prompt "\nLess than one parking space, nothing to do!\n")
           )
           (setvar "osmode" os)
        )
     )
  )
  (setq pt1 nil pt2 nil pt3 nil sta nil ang1 nil ang2 nil str nil ht nil htt nil wid nil)
  (gc)
  (princ)
)
