;PROGRAM PARKLBL LABELS NUMBER OF STALLS
;MODIFIED BY RPR OF NATIONAL SURVEY & ENGINEERING 9/24/91

(defun c:parklbl ()
  (setvar "cmdecho" 0)
  (if (null c:park)(load "park"))
  (if (null stalloff)(c:park))
  (setq bl (getvar "blipmode"))
  (setq sa (getvar "snapang"))
  (setq os (getvar "osmode"))
  (setvar "blipmode" 1)
  (setvar "osmode" 1)
  (while (setq pt1(getpoint "\nStarting point: "))
    (initget 1)
    (setq pt2 (getpoint pt1 "\nEnding point: "))
    (setq sta (fix (/ (distof(rtos(distance pt1 pt2))) stalloff)))
    (setq wid (/ (abs (distance pt1 pt2)) sta))
    (setq ang1 (angle pt1 pt2))
    (setq htt (cdr (assoc 40 (tblsearch "STYLE" (getvar "textstyle")))))
    (setq pt3 (polar (polar pt1 ang1 (/ (* sta wid) 2.0))
        (- ang1 (/ pi 2.0)) htt)
    )
    (if (and (<= ang1 (* pi 1.5)) (> ang1 (* pi 0.5)))
       (setq ang1 (+ ang1 pi))
    )
    (if (> ang1 (* pi 2.0))
       (setq ang1 (- ang1 (* 2.0 pi)))
    )
    (if (> sta 12)
      (setq str (strcat (itoa sta) " spaces @ " (rtos wid) (getvar "dimpost")))
      (setq str (strcat (itoa sta) " @ " (rtos wid) (getvar "dimpost")))
    )
    (setvar "osmode" 0)
    (command "text" "m" pt3 (angtos ang1 (getvar "aunits")(getvar "auprec")) str)
    (setvar "osmode" 1)
  )
  (setvar "blipmode" bl)
  (setvar "osmode" os)
  (setq os nil bl nil sa nil pt1 nil pt2 nil pt3 nil sta nil ang1 nil
        str nil ht nil htt nil wid nil)
  (princ)
)
