(defun isleradpts ()
  (cond
    ((= "ARC" (cdr (assoc 0 (entget e2))))
      (progn
        (setq rpte2 (cdr (assoc 10 (entget e2))))
        (setq re2 (cdr (assoc 40 (entget e2))))
        (if (< (distance pt rpte2) re2)
          (setq rx (- re2 islera) rxmin (- re2 islemin))
          (setq rx (+ re2 islera) rxmin (+ re2 islemin))
        )
        (setq ptx (inters pte11 pte12
             rpte2 (polar rpte2 ang90 1) nil
        ))
        (setq ptx90 (inters (polar pte11 ang90 (- islelen islera))
             (polar pte12 ang90 (- islelen islera))
             rpte2 (polar rpte2 ang90 1) nil
        ))
        (setq ptx270 (inters (polar pte11 ang270 (- islelen islera))
              (polar pte12 ang270 (- islelen islera))
              rpte2 (polar rpte2 ang90 1) nil
        ))
        (setq dx (sqrt (- (expt rxmin 2)(expt (distance ptx rpte2) 2))))
        (setq dx90 (sqrt (- (expt rx 2)(expt (distance ptx90 rpte2) 2))))
        (setq dx270 (sqrt (- (expt rx 2)(expt (distance ptx270 rpte2) 2))))
        (if (> re2 rx)
          (setq ang ang0)
          (setq ang ang180)
        )
        (setq ptmin (polar ptx ang dx))
        (setq rpt2 (polar ptx90 ang dx90))
        (setq rpt3 (polar ptx270 ang dx270))
      )
    )
    ((= "LINE" (cdr (assoc 0 (entget e2))))
      (progn
        (setq pte21 (cdr (assoc 10 (entget e2))))
        (setq pte22 (cdr (assoc 11 (entget e2))))
        (if (< (rem (+ (- (angle pte21 pte22) ang0)(* pi 2))(* pi 2)) pi)
          (setq angx (angle pte21 pte22))
          (setq angx (angle pte22 pte21))
        )
        (setq ang90x (+ angx (/ pi 2.0)))
        (setq ang270x (- angx (/ pi 2.0)))
        (setq ptmin (inters (polar pte21 ang90x islemin)
             (polar pte22 ang90x islemin)
             pte11 pte12 nil
        ))
        (setq rpt2 (inters (polar pte21 ang90x islera)
             (polar pte22 ang90x islera)
             (polar pte11 ang90 (- islelen islera))
             (polar pte12 ang90 (- islelen islera)) nil
        ))
        (setq rpt3 (inters (polar pte21 (+ angx (/ pi 2)) islera)
             (polar pte22 (+ angx (/ pi 2)) islera)
             (polar pte11 ang270 (- islelen islera))
             (polar pte12 ang270 (- islelen islera)) nil
        ))
      )
    )
  )
  (setq ptx (polar ptmin angp0 islerr)
        rpt1 (polar rpt2 ang90 (- islera islerr))
        rpt1 (inters rpt1 (polar rpt1 ang0 1)
                      ptx (polar ptx angp90 1) nil)
        rpt4 (polar rpt3 ang270 (- islera islerr))
        rpt4 (inters rpt4 (polar rpt4 ang0 1)
                      ptx (polar ptx angp270 1) nil)
  )
)

(defun islepts ()
  (setq pt11 (polar rpt1 angp180 islerr)
        pt12 (polar rpt1 ang90 islerr)
        pt21 (polar rpt2 ang90 islera))
  (cond
    ((= "ARC" (cdr (assoc 0 (entget e2))))
      (if (> re2 rx)
        (setq pt22 (polar rpt2 (angle rpte2 rpt2) islera)
              pt31 (polar rpt3 (angle rpte2 rpt3) islera))
        (setq pt22 (polar rpt2 (angle rpt2 rpte2) islera)
              pt31 (polar rpt3 (angle rpt3 rpte2) islera))
      )
    )
    ((= "LINE" (cdr (assoc 0 (entget e2))))
       (setq pt22 (polar rpt2 ang270x islera)
             pt31 (polar rpt3 ang270x islera))
    )
  )
  (setq pt32 (polar rpt3 ang270 islera)
        pt41 (polar rpt4 ang270 islerr)
        pt42 (polar rpt4 angp180 islerr)
        pt10 (inters pte11 pte12 pt11 (polar pt11 angp270 1) nil)
        pt40 (inters pte11 pte12 pt42 (polar pt42 angp90 1) nil)
  )
)

(defun isledraw ()
  (setq oldblip (getvar "blipmode"))
  (setvar "blipmode" 0)
  (cond
    ((= "ARC" (cdr (assoc 0 (entget e2))))
      (command "pline" pt40 pt42 "a" "ce" rpt4 pt41)
      (if (not (equal pt41 pt32 0.0001))(command "l" pt32 "a"))
      (command "ce" rpt3 pt31 pt22 "ce" rpt2 pt21)
      (if (not (equal pt21 pt12 0.0001))(command "l" pt12 "a"))
      (command "ce" rpt1 pt11 "l")
      (if (not (equal pt10 pt40 0.0001))(command pt10))
      (command pt40 "")
    )
    ((= "LINE" (cdr (assoc 0 (entget e2))))
      (command "pline" pt40 pt42 "a" "ce" rpt4 pt41)
      (if (not (equal pt41 pt32 0.0001))(command "l" pt32 "a"))
      (command "ce" rpt3 pt31 "l" pt22 "a" "ce" rpt2 pt21)
      (if (not (equal pt21 pt12 0.0001))(command "l" pt12 "a"))
      (command "ce" rpt1 pt11 "l")
      (if (not (equal pt10 pt40 0.0001))(command pt10))
      (command pt40 "")
    )
  )
  (setvar "blipmode" oldblip)
)

(defun isleadj ()
  (while (or (equal (angle pt12 pt21) ang180 0.0000001)
             (equal (angle pt12 pt21)(+ ang180 (* 2 pi)) 0.0000001)
             (equal (angle pt12 pt21)(- ang180 (* 2 pi)) 0.0000001))
    (setq rpt1 (polar rpt1 ang180 stalloff))
    (islepts)
  )
  (while (or (equal (angle pt41 pt32) ang180 0.0000001)
             (equal (angle pt41 pt32)(+ ang180 (* 2 pi)) 0.0000001)
             (equal (angle pt41 pt32)(- ang180 (* 2 pi)) 0.0000001))
    (setq rpt4 (polar rpt4 ang180 stalloff))
    (islepts)
  )
  (if (and (> (distance pt12 pt21)(/ stalloff 2.0))
           (> (distance pt10 ptmin)(/ stalloff 2.0)))
    (if (< (distance pt12 pt21)(distance pt10 ptmin))
      (setq rpt1 (polar rpt1 ang0 (distance pt12 pt21))
            rpt4 (polar rpt4 ang180 (- stalloff (distance pt12 pt21))))
      (setq rpt1 (polar rpt1 ang0 (distance pt10 ptmin))
            rpt4 (polar rpt4 ang180 (- stalloff (distance pt10 ptmin))))
    )
  )
  (islepts)
  (if (and (> (distance pt41 pt32)(/ stalloff 2.0))
           (> (distance pt40 ptmin)(/ stalloff 2.0)))
    (if (< (distance pt41 pt32)(distance pt40 ptmin))
      (setq rpt4 (polar rpt4 ang0 (distance pt41 pt32))
            rpt1 (polar rpt1 ang180 (- stalloff (distance pt41 pt32))))
      (setq rpt4 (polar rpt4 ang0 (distance pt40 ptmin))
            rpt1 (polar rpt1 ang180 (- stalloff (distance pt40 ptmin))))
    )
  )
  (islepts)
  (if (or (equal (angle pt12 pt21) ang180 0.0000001)
          (equal (angle pt12 pt21)(+ ang180 (* 2 pi)) 0.0000001)
          (equal (angle pt12 pt21)(- ang180 (* 2 pi)) 0.0000001))
    (setq rpt1 (polar rpt1 ang180 (distance pt12 pt21))
          rpt4 (polar rpt4 ang180 (distance pt12 pt21)))
  )
  (islepts)
  (if (or (equal (angle pt41 pt32) ang180 0.0000001)
          (equal (angle pt41 pt32)(+ ang180 (* 2 pi)) 0.0000001)
          (equal (angle pt41 pt32)(- ang180 (* 2 pi)) 0.0000001))
    (setq rpt1 (polar rpt1 ang180 (distance pt41 pt32))
          rpt4 (polar rpt4 ang180 (distance pt41 pt32)))
  )
  (islepts)
)

(defun islesetvar ()
  (setq e2 (car (entsel "\nSelect bounding curbline."))
        pte11 (cdr (assoc 10 (entget e1)))
        pte12 (cdr (assoc 11 (entget e1)))
  )
  (if (<= (distance pt pte11)(distance pt pte12))
    (setq ang0 (angle pte12 pte11))
    (setq ang0 (angle pte11 pte12))
  )
  (setq
        ang90 (+ ang0 (* pi 0.5))
        ang180 (+ ang0 pi)
        ang270 (+ ang0 (* pi 1.5))
        angp0 (- ang0 (* (/ pi 180.0)(- 90.0 isleang)))
        angp90 (+ angp0 (* pi 0.5))
        angp180 (+ angp0 pi)
        angp270 (+ angp0 (* pi 1.50))
  )
  (if (> ang90 (* 2.0 pi))(setq ang90 (- ang90 (* 2.0 pi))))
  (if (> ang180 (* 2.0 pi))(setq ang180 (- ang180 (* 2.0 pi))))
  (if (> ang270 (* 2.0 pi))(setq ang270 (- ang270 (* 2.0 pi))))
)

(defun c:island ()
  (setvar "cmdecho" 0)
  (setq old_err *error* *error* c:nse_err)
  (if (null c:park)(load "park"))
  (c:park)
  (if (= 1 park)
    (while (setq ent (entsel "\nSelect aisle centerline."))
      (setq
            e1 (car ent)
            pt (last ent)
      )
      (if (= "LINE" (cdr (assoc 0 (entget e1))))
        (progn
          (islesetvar)
          (isleradpts)
          (islepts)
          (isleadj)
          (setq e1dat (entget e1))
          (if (> (distance pt10 ptmin)(distance pt40 ptmin))
            (setq ptx pt10)(setq ptx pt40))
          (if (<= (distance pt pte11)(distance pt pte12))
            (setq e1dat (subst (cons 10 ptx) (assoc 10 e1dat) e1dat))
            (setq e1dat (subst (cons 11 ptx) (assoc 11 e1dat) e1dat))
          )
          (entmod e1dat)
          (isledraw)
        )
        (princ "\nSelected aisle centerline is NOT a line!")
      )
    )
  )
  (setq ent nil e1 nil e1dat nil e2 nil re2 nil pt nil
        pte11 nil pte12 nil pte21 nil pte22 nil
        ptx nil ptx90 nil ptx270 nil angx nil ang90x nil ang270x nil
        ang0 nil ang90 nil ang180 nil ang270 nil
        angp0 nil angp90 nil angp180 nil angp270 nil
        dx nil dx90 nil dx270 nil rx nil ptmin nil
        rpt1 nil rpt2 nil rpt3 nil rpt4 nil rpte2 nil
        pt10 nil pt11 nil pt12 nil pt21 nil pt22 nil
        pt31 nil pt32 nil pt40 nil pt41 nil pt42 nil
        oldblip nil *error* old_err old_err nil
  )
  (princ)
)
